FME workspace -- Runee - BOTH - Stage 1 - Headers - CSV Splitter.fmw

Parameters:
- FANOUT_DIRECTORY = C:\TempData\translation_temp   # Fanout Directory

Readers:
- TEXTLINE_1: TEXTLINE from $(FME_MF_DIR)Files for load\headers\*.csv

Writers:
- TEXTLINE_2: TEXTLINE to C:\TempData\translation_temp\a.txt

Note: The headers are read first. / These contain the first line of each CSV file, which is of course the header.
text_line (reader TEXTLINE_1)
    attributes: text_line_data buffer
    -> SubstringExtractor_2
SubstringExtractor_2
    RESULT_ATTR = _Item
    SRC_ATTR = fme_basename
    START = 7
    END = 8
    -> text_line (writer TEXTLINE_2)
Note: Dataset fans out
text_line (writer TEXTLINE_2)
    attributes: text_line_data buffer
