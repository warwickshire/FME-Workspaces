FME workspace -- Runee - COU - Stage 4 - Oracle Loading - INSERT.fmw

Parameters:
- DestDataset_ORACLE8I = co_gistest   # Destination Oracle Spatial Object Service
- SourceDataset_CSV = C:\TempData\addressBase\use\*.txt   # Source Comma Separated Value (CSV) File(s)

Readers:
- CSV_1: CSV from $(SourceDataset_CSV) in BritishNatGrid

Writers:
- ORACLE8I_1: ORACLE8I to $(DestDataset_ORACLE8I) in BritishNatGrid

Note: This workspace simply reads in a series of csv files / that have been pre-split. / It then joins in the attribute values where necessary / from the associated files, and writes it all to the database / as it. / Minimal changes are made to the datastructure. This / way it should be usable by other applications. / It also creates nonspatial indexes on all of the keys, / as well as a few important non-key column (i.e. postcode)
Note: Created by Jonathan Moules / Version 3 - 2014-08-20 / Now updates the requisite tables by truncating them then re-creating them. This is done using the "SQL Statement to Execute Before/After" / Version 2 - 2014-07-29 / - Converted to COU / Version 1 - 2013-08-29 / - Loads all data to the database. / - Adds join values for things that are otherwise in code
Note: Benchmark: / 110,000 features - ~2mins

Bookmark: 11 - Street
Note: 11 - Street
11 (reader CSV_1)
    attributes: RECORD_IDENTIFIER number(3,0), CHANGE_TYPE char(2), PRO_ORDER number(5,0), USRN number(9,0), RECORD_TYPE number(2,0), SWA_ORG_REF_NAMING number(5,0), STATE number(2,0), STATE_DATE char(11), STREET_SURFACE number(2,0), STREET_CLASSIFICATION number(2,0), VERSION number(2,0), STREET_START_DATE char(11), STREET_END_DATE char(1), LAST_UPDATE_DATE char(11), RECORD_ENTRY_DATE char(11), STREET_START_X number(9,2), STREET_START_Y number(9,2), STREET_END_X number(9,2), STREET_END_Y number(9,2), STREET_TOLERANCE number(3,0)
    -> Tester_2
Note: Only Insert and Update features. / "D"elete features are dumped
Tester_2
    TEST_MODE = Automatic
    TEST_DESCRIPTION = ""
    BOOL_OP = OR
    TEST_CLAUSE = TEST @Value(CHANGE_TYPE) != D
    PASSED -> 2DPointAdder_2
2DPointAdder_2
    XVALATTR = @Value(STREET_START_X)
    YVALATTR = @Value(STREET_START_Y)
    -> 2DPointAdder_3
2DPointAdder_3
    XVALATTR = @Value(STREET_END_X)
    YVALATTR = @Value(STREET_END_Y)
    -> Joiner
Note: Join to Street Authority names / (Excel - custodian codes)
Joiner
    MATCH_RULE_DISPLAY = Must Match Exactly One (1:1)
    XLSXR_EXCEL_COL_NAMES = YES
    XLSXR_EXPAND_MERGED_CELLS = Yes
    JOIN_KEYS = SWA_ORG_REF_NAMING Code
    TABLE = Sheet1
    DATASET = $(FME_MF_DIR_ENCODED)Files for load\AddressBaseProducts_LocalCustodianCodesV1_1.xls
    ADDED_FIELDS = Name
    XLSXR_EXPOSED_ATTRS = xlsx_row_id,number(11,0)
    XLSXR_USE_SCHEMA_OTHER_FILES = No
    FORMAT = XLSXR
    JOINED -> AttributeValueMapper
Note: Manual joining for / Record Type
AttributeValueMapper
    DIRECTION = Forward (Source To Destination)
    VAL_ATTR = RECORD_TYPE_TEXT
    DEFAULT_VALUE = @Value(RECORD_TYPE)
    LUT = 1,Official designated street name,2,Street description,3,Numbered street,4,Unofficial street description,9,Description used for LLPG access
    SRC = RECORD_TYPE
    -> AttributeValueMapper_2
Note: Manual joining for / Street State
AttributeValueMapper_2
    DIRECTION = Forward (Source To Destination)
    VAL_ATTR = STREET_STATE
    DEFAULT_VALUE = @Value(STATE)
    LUT = 1,Under Construction,2,Open,4,Permanently Closed
    SRC = STATE
    -> AttributeValueMapper_3
Note: Manual joining for / Street Surface
AttributeValueMapper_3
    DIRECTION = Forward (Source To Destination)
    VAL_ATTR = STREET_SURFACE_TEXT
    DEFAULT_VALUE = @Value(STREET_SURFACE)
    LUT = 1,Metalled,2,UnMetalled,3,Mixed
    SRC = STREET_SURFACE
    -> AttributeValueMapper_4
Note: Manual joining for / Street Classification
AttributeValueMapper_4
    DIRECTION = Forward (Source To Destination)
    VAL_ATTR = STREET_CLASS_TEXT
    DEFAULT_VALUE = @Value(STREET_CLASSIFICATION)
    LUT = 4,Pedestrian way or footpath,6,Cycle track of cycleway,8,All Vehicles,9,Restricted byway,10,Bridleway
    SRC = STREET_CLASSIFICATION
    -> DateFormatter
AttributeRemover
    REMOVE_ATTRS = RECORD_IDENTIFIER,CHANGE_TYPE,PRO_ORDER,RECORD_ENTRY_DATE,_matched_records
    -> AttributeRenamer
AttributeRenamer
    ATTR_LIST = Name,NAMING_AUTHORITY,""
    -> Counter
Counter
    SCOPE = Local
    START = 1
    DOMAIN = counter
    CNT_ATTR = MI_PRINX
    -> OSMM.OS_ABP_STREET (writer ORACLE8I_1)
Note: OSMM.OS_ABP_STREET
OSMM.OS_ABP_STREET (writer ORACLE8I_1)
    attributes: USRN number(8,0), STREET_CLASS_TEXT varchar2(30), STREET_STATE varchar2(20), STREET_SURFACE_TEXT varchar2(10), RECORD_TYPE_TEXT varchar2(35), NAMING_AUTHORITY varchar2(30), STATE_DATE date, LAST_UPDATE_DATE date, STREET_START_DATE date, STREET_END_DATE date, STREET_SURFACE number(1,0), STREET_CLASSIFICATION number(2,0), VERSION number(3,0), RECORD_TYPE number(1,0), STATE number(1,0), SWA_ORG_REF_NAMING number(4,0), STREET_START_X float, STREET_START_Y float, STREET_END_X float, STREET_END_Y float, STREET_TOLERANCE number(3,0), MI_PRINX integer, MI_STYLE varchar2(255)

Bookmark: Date Formatters
DateFormatter
    DATE_ATTR = LAST_UPDATE_DATE
    FMT = FME Date (%Y%m%d)
    SRCFMT = %Y-%m-%d
    -> DateFormatter_2
DateFormatter_2
    DATE_ATTR = STATE_DATE
    FMT = FME Date (%Y%m%d)
    SRCFMT = %Y-%m-%d
    -> DateFormatter_3
DateFormatter_3
    DATE_ATTR = STREET_END_DATE
    FMT = FME Date (%Y%m%d)
    SRCFMT = %Y-%m-%d
    -> DateFormatter_4
DateFormatter_4
    DATE_ATTR = STREET_START_DATE
    FMT = FME Date (%Y%m%d)
    SRCFMT = %Y-%m-%d
    -> AttributeRemover

Bookmark: 21 - BLPU
Note: 21 - Basic Land Property Unit
21 (reader CSV_1)
    attributes: RECORD_IDENTIFIER number(3,0), CHANGE_TYPE char(2), PRO_ORDER number(6,0), UPRN number(13,0), LOGICAL_STATUS number(2,0), BLPU_STATE number(2,0), BLPU_STATE_DATE char(11), PARENT_UPRN number(13,0), X_COORDINATE number(9,2), Y_COORDINATE number(9,2), RPC number(2,0), LOCAL_CUSTODIAN_CODE number(5,0), START_DATE char(11), END_DATE char(11), LAST_UPDATE_DATE char(11), ENTRY_DATE char(11), POSTAL_ADDRESS char(2), POSTCODE_LOCATOR char(8), MULTI_OCC_COUNT number(3,0)
    -> Tester_3
Tester_3
    TEST_MODE = Automatic
    TEST_DESCRIPTION = ""
    BOOL_OP = OR
    TEST_CLAUSE = TEST @Value(CHANGE_TYPE) != D
    PASSED -> 2DPointAdder
2DPointAdder
    XVALATTR = @Value(X_COORDINATE)
    YVALATTR = @Value(Y_COORDINATE)
    -> Joiner_2
Note: Join to Local Authority names / (Excel - custodian codes)
Joiner_2
    MATCH_RULE_DISPLAY = Must Match Exactly One (1:1)
    XLSXR_EXCEL_COL_NAMES = YES
    XLSXR_EXPAND_MERGED_CELLS = Yes
    JOIN_KEYS = LOCAL_CUSTODIAN_CODE Code
    TABLE = Sheet1
    DATASET = $(FME_MF_DIR_ENCODED)Files for load\AddressBaseProducts_LocalCustodianCodesV1_1.xls
    ADDED_FIELDS = Name
    XLSXR_EXPOSED_ATTRS = xlsx_row_id,number(11,0)
    XLSXR_USE_SCHEMA_OTHER_FILES = No
    FORMAT = XLSXR
    JOINED -> AttributeValueMapper_5
Note: Manual joining for / Logical Status
AttributeValueMapper_5
    DIRECTION = Forward (Source To Destination)
    VAL_ATTR = LOGICAL_STATUS_TEXT
    DEFAULT_VALUE = @Value(LOGICAL_STATUS)
    LUT = 1,Approved,3,Alternative,6,Provisional,8,Historical
    SRC = LOGICAL_STATUS
    -> AttributeValueMapper_6
Note: Manual joining for / BLPU State
AttributeValueMapper_6
    DIRECTION = Forward (Source To Destination)
    VAL_ATTR = BLPU_STATE_TEXT
    DEFAULT_VALUE = Unknown / Not Applicable
    LUT = 1,Under construction,2,In use,3,Unoccupied,4,No longer existing,6,Planning permission granted
    SRC = BLPU_STATE
    -> AttributeValueMapper_7
Note: Manual joining for / Representative Point Code / (Point Type)
AttributeValueMapper_7
    DIRECTION = Forward (Source To Destination)
    VAL_ATTR = RPC_TEXT
    DEFAULT_VALUE = @Value(RPC)
    LUT = 1,Visual centre,2,General internal point,3,SW corner of reference 100m grid,4,Start of referenced street,5,General point based on postcode unit,9,Centre of a contributing authority area
    SRC = RPC
    -> AttributeValueMapper_8
Note: Manual joining for / Post code type
AttributeValueMapper_8
    DIRECTION = Forward (Source To Destination)
    VAL_ATTR = POSTAL_ADDRESS_TEXT
    DEFAULT_VALUE = @Value(POSTAL_ADDRESS)
    LUT = S,Single address,N,Not a postal address,C,Multi-occupancy (child) address,M,Multi-occupancy (parent) address
    SRC = POSTAL_ADDRESS
    -> DateFormatter_5
AttributeRemover_2
    REMOVE_ATTRS = RECORD_IDENTIFIER,CHANGE_TYPE,PRO_ORDER,ENTRY_DATE,_matched_records
    -> AttributeRenamer_2
AttributeRenamer_2
    ATTR_LIST = RPC_TEXT,POINT_TYPE,"",Name,CUSTODIAN_NAME,""
    -> Counter_2
Counter_2
    SCOPE = Local
    START = 1
    DOMAIN = counter
    CNT_ATTR = MI_PRINX
    -> OSMM.OS_ABP_BLPU (writer ORACLE8I_1)
Note: OSMM.OS_ABP_BLPU
OSMM.OS_ABP_BLPU (writer ORACLE8I_1)
    attributes: UPRN varchar2(12), POSTCODE_LOCATOR varchar2(8), BLPU_STATE_TEXT varchar2(30), POINT_TYPE varchar2(50), POSTAL_ADDRESS_TEXT varchar2(35), LOGICAL_STATUS_TEXT varchar2(12), CUSTODIAN_NAME varchar2(30), MULTI_OCC_COUNT number(4,0), PARENT_UPRN varchar2(12), LOGICAL_STATUS number(1,0), RPC number(1,0), LOCAL_CUSTODIAN_CODE number(4,0), POSTAL_ADDRESS varchar2(1), BLPU_STATE number(1,0), BLPU_STATE_DATE date, LAST_UPDATE_DATE date, START_DATE date, END_DATE date, X_COORDINATE float, Y_COORDINATE float, MI_PRINX integer, MI_STYLE varchar2(255)

Bookmark: Date Formatters
DateFormatter_5
    DATE_ATTR = LAST_UPDATE_DATE
    FMT = FME Date (%Y%m%d)
    SRCFMT = %Y-%m-%d
    -> DateFormatter_6
DateFormatter_6
    DATE_ATTR = BLPU_STATE_DATE
    FMT = FME Date (%Y%m%d)
    SRCFMT = %Y-%m-%d
    -> DateFormatter_7
DateFormatter_7
    DATE_ATTR = END_DATE
    FMT = FME Date (%Y%m%d)
    SRCFMT = %Y-%m-%d
    -> DateFormatter_8
DateFormatter_8
    DATE_ATTR = START_DATE
    FMT = FME Date (%Y%m%d)
    SRCFMT = %Y-%m-%d
    -> AttributeRemover_2

Bookmark: 15 - Street Descriptor
Note: 15 - Street Descriptor
15 (reader CSV_1)
    attributes: RECORD_IDENTIFIER number(3,0), CHANGE_TYPE char(2), PRO_ORDER number(5,0), USRN number(9,0), STREET_DESCRIPTION char(61), LOCALITY_NAME char(28), TOWN_NAME char(7), ADMINISTRATIVE_AREA char(6), LANGUAGE char(4)
    -> Tester_4
Tester_4
    TEST_MODE = Automatic
    TEST_DESCRIPTION = ""
    BOOL_OP = OR
    TEST_CLAUSE = TEST @Value(CHANGE_TYPE) != D
    PASSED -> AttributeRemover_3
Note: Much as I want to delete it, "Language" / must be kept because it's used as a key.
AttributeRemover_3
    REMOVE_ATTRS = RECORD_IDENTIFIER,CHANGE_TYPE,PRO_ORDER
    -> Counter_3
Counter_3
    SCOPE = Local
    START = 1
    DOMAIN = counter
    CNT_ATTR = MI_PRINX
    -> OSMM.OS_ABP_STREET_DESCRIPTOR (writer ORACLE8I_1)
Note: OS_ABP_STREET_DESCRIPTOR
OSMM.OS_ABP_STREET_DESCRIPTOR (writer ORACLE8I_1)
    attributes: USRN number(8,0), STREET_DESCRIPTION varchar2(100), LOCALITY_NAME varchar2(35), TOWN_NAME varchar2(30), ADMINISTRATIVE_AREA varchar2(30), LANGUAGE varchar2(3), MI_PRINX integer

Bookmark: 23 - Application Cross Reference
Note: 23 - Application Cross Reference
23 (reader CSV_1)
    attributes: RECORD_IDENTIFIER number(3,0), CHANGE_TYPE char(2), PRO_ORDER number(6,0), UPRN number(13,0), XREF_KEY char(15), CROSS_REFERENCE char(21), VERSION number(3,0), SOURCE char(7), START_DATE char(11), END_DATE char(1), LAST_UPDATE_DATE char(11), ENTRY_DATE char(11)
    -> Tester_5
Tester_5
    TEST_MODE = Automatic
    TEST_DESCRIPTION = ""
    BOOL_OP = OR
    TEST_CLAUSE = TEST @Value(CHANGE_TYPE) != D
    PASSED -> AttributeValueMapper_9
AttributeValueMapper_9
    DIRECTION = Forward (Source To Destination)
    VAL_ATTR = SOURCE_TEXT
    DEFAULT_VALUE = @Value(SOURCE)
    LUT = 7666MT,OS MasterMap Topographic Layer TOID,7666MA,OS MasterMap AddressLayer 2 TOID,7666MI,OS MasterMap ITN TOID,7666VC,Centrally created council tax,7666VN,Centrally created non-domestic rates,7666OW,ONS Ward Code,7666OP,ONS Parish Code
    SRC = SOURCE
    -> DateFormatter_9
AttributeRemover_4
    REMOVE_ATTRS = RECORD_IDENTIFIER,CHANGE_TYPE,PRO_ORDER,ENTRY_DATE
    -> Counter_4
Counter_4
    SCOPE = Local
    START = 1
    DOMAIN = counter
    CNT_ATTR = MI_PRINX
    -> OSMM.OS_ABP_APPLICATION_XREF (writer ORACLE8I_1)
Note: OS_ABP_APPLICATION_XREF
OSMM.OS_ABP_APPLICATION_XREF (writer ORACLE8I_1)
    attributes: UPRN varchar2(12), SOURCE_TEXT varchar2(40), CROSS_REFERENCE varchar2(50), VERSION number(3,0), SOURCE varchar2(6), XREF_KEY varchar2(14), LAST_UPDATE_DATE date, START_DATE date, END_DATE date, MI_PRINX integer

Bookmark: Date Formatters
DateFormatter_9
    DATE_ATTR = LAST_UPDATE_DATE
    FMT = FME Date (%Y%m%d)
    SRCFMT = %Y-%m-%d
    -> DateFormatter_10
DateFormatter_10
    DATE_ATTR = END_DATE
    FMT = FME Date (%Y%m%d)
    SRCFMT = %Y-%m-%d
    -> DateFormatter_11
DateFormatter_11
    DATE_ATTR = START_DATE
    FMT = FME Date (%Y%m%d)
    SRCFMT = %Y-%m-%d
    -> AttributeRemover_4

Bookmark: 24 - Local Property Identifier
Note: 24 - Local Property Identifier
24 (reader CSV_1)
    attributes: RECORD_IDENTIFIER number(3,0), CHANGE_TYPE char(2), PRO_ORDER number(6,0), UPRN number(13,0), LPI_KEY char(15), LANGUAGE char(4), LOGICAL_STATUS number(2,0), START_DATE char(11), END_DATE char(11), LAST_UPDATE_DATE char(11), ENTRY_DATE char(11), SAO_START_NUMBER number(4,0), SAO_START_SUFFIX char(2), SAO_END_NUMBER number(2,0), SAO_END_SUFFIX char(1), SAO_TEXT char(61), PAO_START_NUMBER number(4,0), PAO_START_SUFFIX char(2), PAO_END_NUMBER number(4,0), PAO_END_SUFFIX char(1), PAO_TEXT char(57), USRN number(9,0), USRN_MATCH_INDICATOR number(2,0), AREA_NAME char(1), LEVEL char(1), OFFICIAL_FLAG char(2)
    -> Tester_6
Tester_6
    TEST_MODE = Automatic
    TEST_DESCRIPTION = ""
    BOOL_OP = OR
    TEST_CLAUSE = TEST @Value(CHANGE_TYPE) != D
    PASSED -> AttributeValueMapper_10
Note: Manual joining for / Logical Status
AttributeValueMapper_10
    DIRECTION = Forward (Source To Destination)
    VAL_ATTR = LOGICAL_STATUS_TEXT
    DEFAULT_VALUE = @Value(LOGICAL_STATUS)
    LUT = 1,Approved,3,Alternative,6,Provisional,8,Historical
    SRC = LOGICAL_STATUS
    -> DateFormatter_12
AttributeRemover_5
    REMOVE_ATTRS = RECORD_IDENTIFIER,CHANGE_TYPE,PRO_ORDER,LANGUAGE,ENTRY_DATE
    -> Counter_5
Counter_5
    SCOPE = Local
    START = 1
    DOMAIN = counter
    CNT_ATTR = MI_PRINX
    -> OSMM.OS_ABP_LPI (writer ORACLE8I_1)
Note: OS_ABP_LPI
OSMM.OS_ABP_LPI (writer ORACLE8I_1)
    attributes: UPRN varchar2(12), SAO_START_NUMBER number(4,0), SAO_START_SUFFIX varchar2(2), SAO_END_NUMBER number(4,0), SAO_END_SUFFIX varchar2(2), SAO_TEXT varchar2(90), PAO_START_NUMBER number(4,0), PAO_START_SUFFIX varchar2(2), PAO_END_NUMBER number(4,0), PAO_END_SUFFIX varchar2(2), PAO_TEXT varchar2(90), LOGICAL_STATUS_TEXT varchar2(12), AREA_NAME varchar2(35), LEVEL varchar2(30), OFFICIAL_FLAG varchar2(1), LOGICAL_STATUS varchar2(1), LAST_UPDATE_DATE date, START_DATE date, END_DATE date, USRN number(8,0), USRN_MATCH_INDICATOR varchar2(1), LPI_KEY varchar2(14), MI_PRINX integer

Bookmark: Date Formatters
DateFormatter_12
    DATE_ATTR = LAST_UPDATE_DATE
    FMT = FME Date (%Y%m%d)
    SRCFMT = %Y-%m-%d
    -> DateFormatter_13
DateFormatter_13
    DATE_ATTR = END_DATE
    FMT = FME Date (%Y%m%d)
    SRCFMT = %Y-%m-%d
    -> DateFormatter_14
DateFormatter_14
    DATE_ATTR = START_DATE
    FMT = FME Date (%Y%m%d)
    SRCFMT = %Y-%m-%d
    -> AttributeRemover_5

Bookmark: 28 - Delivery Point Address
Note: 28 - Delivery Point Address
28 (reader CSV_1)
    attributes: RECORD_IDENTIFIER number(3,0), CHANGE_TYPE char(2), PRO_ORDER number(6,0), UPRN number(13,0), PARENT_ADDRESSABLE_UPRN number(13,0), UDPRN number(9,0), ORGANISATION_NAME char(48), DEPARTMENT_NAME char(38), SUB_BUILDING_NAME char(26), BUILDING_NAME char(35), BUILDING_NUMBER number(4,0), DEPENDENT_THOROUGHFARE_NAME char(28), THROUGHFARE_NAME char(24), DOUBLE_DEPENDENT_LOCALITY char(1), DEPENDENT_LOCALITY char(28), POST_TOWN char(7), POSTCODE char(8), POSTCODE_TYPE char(2), WELSH_DEPENDENT_THOROUGHFARE char(1), WELSH_THOROUGHFARE_NAME char(1), WELSH_DOUBLE_DEPENDENT_LOCALITY char(1), WELSH_DEPENDENT_LOCALITY char(1), WELSH_POST_TOWN char(1), PO_BOX_NUMBER char(1), PROCESS_DATE char(11), START_DATE char(11), END_DATE char(11), LAST_UPDATE_DATE char(11), ENTRY_DATE char(11)
    -> Tester_7
Tester_7
    TEST_MODE = Automatic
    TEST_DESCRIPTION = ""
    BOOL_OP = OR
    TEST_CLAUSE = TEST @Value(CHANGE_TYPE) != D
    PASSED -> DateFormatter_15
AttributeRenamer_3
    ATTR_LIST = UDPRN,RM_UDPRN,""
    -> AttributeRemover_6
AttributeRemover_6
    REMOVE_ATTRS = RECORD_IDENTIFIER,CHANGE_TYPE,PRO_ORDER,WELSH_DEPENDENT_THOROUGHFARE,WELSH_THOROUGHFARE_NAME,WELSH_DOUBLE_DEPENDENT_LOCALITY,WELSH_DEPENDENT_LOCALITY,WELSH_POST_TOWN,ENTRY_DATE
    -> Counter_6
Counter_6
    SCOPE = Local
    START = 1
    DOMAIN = counter
    CNT_ATTR = MI_PRINX
    -> OSMM.OS_ABP_DELIVERY_POINT_ADDR (writer ORACLE8I_1)
Note: OS_ABP_DELIVERY_POINT_ADDR
OSMM.OS_ABP_DELIVERY_POINT_ADDR (writer ORACLE8I_1)
    attributes: UPRN varchar2(12), ORGANISATION_NAME varchar2(60), DEPARTMENT_NAME varchar2(60), SUB_BUILDING_NAME varchar2(30), BUILDING_NAME varchar2(50), BUILDING_NUMBER number(4,0), DEPENDENT_THOROUGHFARE_NAME varchar2(80), THROUGHFARE_NAME varchar2(80), DOUBLE_DEPENDENT_LOCALITY varchar2(35), DEPENDENT_LOCALITY varchar2(35), POST_TOWN varchar2(30), POSTCODE varchar2(8), POSTCODE_TYPE varchar2(1), RM_UDPRN number(8,0), PARENT_ADDRESSABLE_UPRN varchar2(12), PO_BOX_NUMBER varchar2(6), PROCESS_DATE date, START_DATE date, END_DATE date, LAST_UPDATE_DATE date, MI_PRINX integer

Bookmark: Date Formatters
DateFormatter_15
    DATE_ATTR = LAST_UPDATE_DATE
    FMT = FME Date (%Y%m%d)
    SRCFMT = %Y-%m-%d
    -> DateFormatter_16
DateFormatter_16
    DATE_ATTR = PROCESS_DATE
    FMT = FME Date (%Y%m%d)
    SRCFMT = %Y-%m-%d
    -> DateFormatter_17
DateFormatter_17
    DATE_ATTR = END_DATE
    FMT = FME Date (%Y%m%d)
    SRCFMT = %Y-%m-%d
    -> DateFormatter_18
DateFormatter_18
    DATE_ATTR = START_DATE
    FMT = FME Date (%Y%m%d)
    SRCFMT = %Y-%m-%d
    -> AttributeRenamer_3

Bookmark: 30 - Successor
Note: 30 - Successor
30 (reader CSV_1) [off]
    -> AttributeRemover_7
Note: Disabled because there's no data and I have no clue what it is for.
AttributeRemover_7
    -> Counter_7
Counter_7
    SCOPE = Local
    START = 1
    DOMAIN = counter
    CNT_ATTR = MI_PRINX
    -> OSMM.OS_ABP_SUCCESSOR (writer ORACLE8I_1)
Note: OS_ABP_SUCCESSOR
OSMM.OS_ABP_SUCCESSOR (writer ORACLE8I_1) [off]
    attributes: MI_PRINX integer

Bookmark: 31 - Organisation
Note: 31 - Organisation
31 (reader CSV_1)
    attributes: RECORD_IDENTIFIER number(3,0), CHANGE_TYPE char(2), PRO_ORDER number(7,0), UPRN number(13,0), ORG_KEY char(15), ORGANISATION char(55), LEGAL_NAME char(1), START_DATE char(11), END_DATE char(1), LAST_UPDATE_DATE char(11), ENTRY_DATE char(11)
    -> Tester_8
Tester_8
    TEST_MODE = Automatic
    TEST_DESCRIPTION = ""
    BOOL_OP = OR
    TEST_CLAUSE = TEST @Value(CHANGE_TYPE) != D
    PASSED -> DateFormatter_19
AttributeRemover_8
    REMOVE_ATTRS = RECORD_IDENTIFIER,CHANGE_TYPE,PRO_ORDER,ENTRY_DATE
    -> Counter_8
Counter_8
    SCOPE = Local
    START = 1
    DOMAIN = counter
    CNT_ATTR = MI_PRINX
    -> OSMM.OS_ABP_ORGANISATION (writer ORACLE8I_1)
Note: OS_ABP_ORGANISATION
OSMM.OS_ABP_ORGANISATION (writer ORACLE8I_1)
    attributes: UPRN varchar2(12), ORGANISATION varchar2(100), LEGAL_NAME varchar2(60), ORG_KEY varchar2(14), LAST_UPDATE_DATE date, START_DATE date, END_DATE date, MI_PRINX integer

Bookmark: Date Formatters
DateFormatter_19
    DATE_ATTR = LAST_UPDATE_DATE
    FMT = FME Date (%Y%m%d)
    SRCFMT = %Y-%m-%d
    -> DateFormatter_20
DateFormatter_20
    DATE_ATTR = END_DATE
    FMT = FME Date (%Y%m%d)
    SRCFMT = %Y-%m-%d
    -> DateFormatter_21
DateFormatter_21
    DATE_ATTR = START_DATE
    FMT = FME Date (%Y%m%d)
    SRCFMT = %Y-%m-%d
    -> AttributeRemover_8

Bookmark: 32 Classification
Note: 32 Classification
32 (reader CSV_1)
    attributes: RECORD_IDENTIFIER number(3,0), CHANGE_TYPE char(2), PRO_ORDER number(6,0), UPRN number(13,0), CLASS_KEY char(15), CLASSIFICATION_CODE char(5), CLASS_SCHEME char(42), SCHEME_VERSION number(3,1), START_DATE char(11), END_DATE char(11), LAST_UPDATE_DATE char(11), ENTRY_DATE char(11)
    -> Tester_9
Tester_9
    TEST_MODE = Automatic
    TEST_DESCRIPTION = ""
    BOOL_OP = OR
    TEST_CLAUSE = TEST @Value(CHANGE_TYPE) != D
    PASSED -> Joiner_3
Note: Join to Classifications / (CSV)
Joiner_3
    CSV__GROUP_BY_DATASET = yes
    CSV__SKIP_LINES = 1
    CSV__ALLOW_SPACES_IN_COLUMN_NAMES = yes
    MATCH_RULE_DISPLAY = Must Match Exactly One (1:1)
    JOIN_KEYS = CLASSIFICATION_CODE Concatenated
    CSV__STRIP_QUOTES = yes
    CSV__FIELD_NAMES_AFTER_HEADER = no
    CSV_SCAN_MAX_FEATURES = 10000
    TABLE = Sheet1
    CSV__SCHEMA_WITH_COL_NAMES = Concatenated,char,7,,Primary_Desc,char,29,,Secondary_Desc,char,120,,Tertiary_Desc,char,113,,Quaternary_Desc,char,51,
    CSV__IN_SEPARATOR = ,
    DATASET = $(FME_MF_DIR_ENCODED)Files for load\AddressBase_products_classification_scheme_1.3.csv
    CSV__SCHEMA = char,7,,char,29,,char,120,,char,113,,char,51,
    ADDED_FIELDS = Class_Desc Primary_Code Secondary_Code Tertiary_Code Quaternary_Code Primary_Desc Secondary_Desc Tertiary_Desc Quaternary_Desc
    CSV__DUPLICATE_DELIMS = no
    CSV__IN_FIELD_NAMES = YES
    CSV__SKIP_FOOTER = 0
    FORMAT = CSV
    JOINED -> DateFormatter_22
AttributeRenamer_4
    ATTR_LIST = Primary_Desc,PRIMARY_CLASS,"",Secondary_Desc,SECONDARY_CLASS,"",Tertiary_Desc,TERTIARY_CLASS,"",Quaternary_Desc,QUATERNARY_CLASS,"",Primary_Code,PRIMARY_CODE,"",Secondary_Code,SECONDARY_CODE,"",Tertiary_Code,TERTIARY_CODE,"",Quaternary_Code,QUATERNARY_CODE,"",Class_Desc,CLASS_DESCRIPTION,""
    -> AttributeRemover_9
AttributeRemover_9
    REMOVE_ATTRS = RECORD_IDENTIFIER,CHANGE_TYPE,PRO_ORDER,ENTRY_DATE,_matched_records
    -> Counter_9
Counter_9
    SCOPE = Local
    START = 1
    DOMAIN = counter
    CNT_ATTR = MI_PRINX
    -> OSMM.OS_ABP_CLASSIFICATION (writer ORACLE8I_1)
Note: OS_ABP_CLASSIFICATION
OSMM.OS_ABP_CLASSIFICATION (writer ORACLE8I_1)
    attributes: UPRN varchar2(12), CLASSIFICATION_CODE varchar2(6), CLASS_DESCRIPTION varchar2(130), PRIMARY_CLASS varchar2(30), SECONDARY_CLASS varchar2(120), TERTIARY_CLASS varchar2(120), QUATERNARY_CLASS varchar2(60), PRIMARY_CODE varchar2(2), SECONDARY_CODE varchar2(2), TERTIARY_CODE integer, QUATERNARY_CODE varchar2(3), CLASS_KEY varchar2(14), START_DATE date, END_DATE date, LAST_UPDATE_DATE date, CLASS_SCHEME varchar2(60), SCHEME_VERSION float, MI_PRINX integer

Bookmark: Date Formatters
DateFormatter_22
    DATE_ATTR = LAST_UPDATE_DATE
    FMT = FME Date (%Y%m%d)
    SRCFMT = %Y-%m-%d
    -> DateFormatter_23
DateFormatter_23
    DATE_ATTR = END_DATE
    FMT = FME Date (%Y%m%d)
    SRCFMT = %Y-%m-%d
    -> DateFormatter_24
DateFormatter_24
    DATE_ATTR = START_DATE
    FMT = FME Date (%Y%m%d)
    SRCFMT = %Y-%m-%d
    -> AttributeRenamer_4

Bookmark: Spatial Data
Note: 21 (BLPU) has X/Y / 11 (Street) has street start/stop points
Note: Bug in DateFormatter (2013SP3) / means we need one for each to be / sure change happens.
