FME workspace _1 _ OS_Raster_Creator_RUNNER.fmw

Note: Created by Jonathan Moules / On 2013-10-23 / It is designed to feed hardcoded parameters / to a more generic raster building workspace. / This way OS rasters can be created automatically / and easily.
Note: Benchmark: / - About 5hrs (VML takes longest) / - About 15GB RAM (VML again)
Creator
    COORDSYS = BritishNatGrid
    NUM = 1
    GEOMTYPE = Geometry Object
    CREATED -> Placeholder
Note: HOW TO USE / 1. Make sure new TIF files are downloaded and placed on Q drive in the right location / 2. Press Play / 3. Output files are in: / - D:\Raster_Outputs\
Placeholder: AttributeRemover
    -> MiniScale
    -> 250_000
    -> 50_000
    -> 25_000
    -> VectorMap_District
    -> VectorMap_Local
    -> Street_View
Placeholder_2: AttributeRemover
    -> WorkspaceRunner
WorkspaceRunner
    WORKSPACE_FILE = $(FME_MF_DIR)OS_Raster_Ultimate_Processor.fmw
    BLOCKING = No
    WORKSPACE_PARAMETERS = SourceDataset_TIFF_3,@Value(INPUT_TIF_DIR),output_format,@Value(FORMATS),out_name,@Value(PRODUCT_NAME),TIFF_IN_SEARCH_ENVELOPE_MINX_TIFF,@Value(BBOX_MINX),TIFF_IN_SEARCH_ENVELOPE_MINY_TIFF,@Value(BBOX_MINY),TIFF_IN_SEARCH_ENVELOPE_MAXX_TIFF,@Value(BBOX_MAXX),TIFF_IN_SEARCH_ENVELOPE_MAXY_TIFF,@Value(BBOX_MAXY),MOSAIC,@Value(MOSAIC),DestDataset_all_formats,D:\outputs
    MAX_PROC = 8
    SUCCEEDED -> Logger_SUCCEEDED
    FAILED -> Logger_FAILED
    SUMMARY -> Logger_SUMMARY
Logger_SUCCEEDED
    MESSAGE = Feature is:
    MAXFEATS = 20
    MAXCOORDS = 20
Logger_FAILED
    MESSAGE = Feature is:
    MAXFEATS = 20
    MAXCOORDS = 20
Logger_SUMMARY
    MESSAGE = Feature is:
    MAXFEATS = 20
    MAXCOORDS = 20

Bookmark: Configure here
Note: MiniScale / !!!This may require pointing at the correct file!!! / (The OS renames them each version)
MiniScale: AttributeCreator
    ATTR_LIST = BBOX_MINX,0,BBOX_MINY,0,BBOX_MAXX,0,BBOX_MAXY,0,INPUT_TIF_DIR,Q:\GIS_DATA\ORDNANCE_SURVEY_BASEMAPS\OS_MiniScale\TIF\MiniScale_(standard)_R16.tif,PRODUCT_NAME,OS_Miniscale,MOSAIC,Don't Mosaic,FORMATS,JP2(BW) JP2(Col) GTF(Col)
    -> Placeholder_2
250_000: AttributeCreator
    ATTR_LIST = BBOX_MINX,0,BBOX_MINY,0,BBOX_MAXX,0,BBOX_MAXY,0,INPUT_TIF_DIR,Q:\GIS_DATA\ORDNANCE_SURVEY_BASEMAPS\OS_250000\TIF\*.tif,PRODUCT_NAME,OS_250000,MOSAIC,Mosaic,FORMATS,JP2(BW) JP2(Col) GTF(Col)
    -> Placeholder_2
50_000: AttributeCreator
    ATTR_LIST = BBOX_MINX,400001,BBOX_MINY,220001,BBOX_MAXX,459999,BBOX_MAXY,319999,INPUT_TIF_DIR,Q:\GIS_DATA\ORDNANCE_SURVEY_BASEMAPS\OS_50000\TIF\*.tif,PRODUCT_NAME,OS_50000,MOSAIC,Mosaic,FORMATS,JP2(BW) JP2(Col) GTF(Col)
    -> Placeholder_2
25_000: AttributeCreator
    ATTR_LIST = BBOX_MINX,400001,BBOX_MINY,220001,BBOX_MAXX,459999,BBOX_MAXY,319999,INPUT_TIF_DIR,Q:\GIS_DATA\ORDNANCE_SURVEY_BASEMAPS\OS_25000\TIF\*.tif,PRODUCT_NAME,OS_25000,MOSAIC,Mosaic,FORMATS,JP2(BW) JP2(Col) GTF(Col)
    -> Placeholder_2
VectorMap_District: AttributeCreator
    ATTR_LIST = BBOX_MINX,400001,BBOX_MINY,220001,BBOX_MAXX,459999,BBOX_MAXY,319999,INPUT_TIF_DIR,Q:\GIS_DATA\ORDNANCE_SURVEY_BASEMAPS\OS_VectorMap_District\TIF\*.tif,PRODUCT_NAME,OS_VectorMap_District,MOSAIC,Mosaic,FORMATS,JP2(BW) JP2(Col) GTF(Col)
    -> Placeholder_2
VectorMap_Local: AttributeCreator
    ATTR_LIST = BBOX_MINX,400001,BBOX_MINY,220001,BBOX_MAXX,459999,BBOX_MAXY,319999,INPUT_TIF_DIR,Q:\GIS_DATA\ORDNANCE_SURVEY_BASEMAPS\OS_VectorMap_Local\TIF\*.tif,PRODUCT_NAME,OS_VectorMap_Local,MOSAIC,Mosaic,FORMATS,JP2(BW) JP2(Col) GTF(Col)
    -> Placeholder_2
Street_View: AttributeCreator
    ATTR_LIST = BBOX_MINX,400001,BBOX_MINY,220001,BBOX_MAXX,459999,BBOX_MAXY,319999,INPUT_TIF_DIR,Q:\GIS_DATA\ORDNANCE_SURVEY_BASEMAPS\OS_STREET-VIEW\TIF\*.tif,PRODUCT_NAME,OS_Street_View,MOSAIC,Mosaic,FORMATS,JP2(BW) JP2(Col) GTF(Col)
    -> Placeholder_2
