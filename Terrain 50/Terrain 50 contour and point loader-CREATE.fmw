FME workspace Terrain 50 contour and point loader-CREATE.fmw

Parameters:
- DestDataset_ORACLE8I = co_gislive   # Destination Oracle Spatial Object Service
- SourceDataset_SHAPE = Q:\GIS_DATA\ZZ Original GIS Data\01 Ordnance Survey\Terrain 50\2013-11-06\Contours_points\**\*.zip\**\*.shp   # Source Esri Shape File(s)
- FEATURE_TYPES =

Readers:
- SHAPE_1: SHAPE from $(SourceDataset_SHAPE) in BritishNatGrid

Writers:
- ORACLE8I_1: ORACLE8I to $(DestDataset_ORACLE8I) in BritishNatGrid

SP36NE_line (reader SHAPE_1)
    attributes: ID char(20), FEAT_TYPE char(17), SUB_TYPE char(13), PROP_VALUE number(7,2)
    -> AttributeRemover_2
AttributeRemover_2
    REMOVE_ATTRS = ID,FEAT_TYPE
    -> GeometryFilter
GeometryFilter
    BREAK_AGG = No
    POINT -> AttributeRenamer_2
    LINE -> GeometryValidator_2
AttributeRenamer_2
    ATTR_LIST = SUB_TYPE,POINT_TYPE,"",PROP_VALUE,HEIGHT,""
    -> Counter_2
Counter_2
    SCOPE = Local
    START = 1
    DOMAIN = counter
    CNT_ATTR = MI_PRINX
    -> StringFormatter_2
Note: Ensure the "height" attribute / is in a format Oracle won't cry about
StringFormatter_2
    SRC_ATTRS = HEIGHT
    FORMAT = .2f
    -> OSMM.OS_TERRAIN_50_POINTS (writer ORACLE8I_1)
OSMM.OS_TERRAIN_50_POINTS (writer ORACLE8I_1) [off]
    attributes: HEIGHT float, POINT_TYPE varchar2(12), MI_PRINX integer, MI_STYLE varchar2(250)
Note: Data validation. / Just in case.
GeometryValidator_2
    CHECK_HOLE_TOUCHING_POLYGON = No
    DUP_COORDS_CHECK_Z = Yes
    NULL_REMOVAL = NULL_REMOVAL
    TYPE_REPAIR = TYPE_REPAIR
    SELF_INTERSECTING = SELF_INTERSECTING
    PRESETS = OGC
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = Yes
    PLANAR_TOLERANCE_MODE = Auto
    NAN_REMOVAL = NAN_REMOVAL
    CONSECUTIVE_IDENTICAL_VERTICES_2D = CONSECUTIVE_IDENTICAL_VERTICES_2D
    PASSED -> LineJoiner
    REPAIRED -> LineJoiner
Note: This joins the contours together that have been split due to / being supplied on a different tile. / Must group by both feature_code (as there are two) and Height.
LineJoiner
    GROUP_BY = SUB_TYPE PROP_VALUE
    GROUP_BREAK = no
    PRESERVE = no
    TOPOLOGY = End noded
    CONSIDER_NODE_ELEVATION = yes
    BREAK = no
    LINE -> AttributeRenamer
AttributeRenamer
    ATTR_LIST = SUB_TYPE,CONTOUR_TYPE,"",PROP_VALUE,HEIGHT,""
    -> Intersector_2
Note: Otherwise some self-intersections / may slip through. / And then ArcSDE will cry!
Intersector_2
    DUPLICATE_Z_NODES = No
    SEPARATE_COLLINEAR_SEGMENTS = No
    PERFORM_SELF_INTERSECTION = Yes
    OV_ATTR = ___a
    INTERSECTED -> Counter
Counter
    SCOPE = Local
    START = 1
    DOMAIN = counter
    CNT_ATTR = MI_PRINX
    -> OSMM.OS_TERRAIN_50_CONTOURS (writer ORACLE8I_1)
OSMM.OS_TERRAIN_50_CONTOURS (writer ORACLE8I_1)
    attributes: HEIGHT float, CONTOUR_TYPE varchar2(12), MI_PRINX integer, MI_STYLE varchar2(250)
