FME workspace Terrain 50 - ASCII grid mosaicer.fmw

Parameters:
- SourceDataset_ESRIASCIIGRID = Q:\GIS_DATA\ZZ Original GIS Data\Ordnance Survey\Terrain 50\2013-11-06\ASCII_grid\**\*.zip   # Source Esri ASCII Grid File(s)
- FEATURE_TYPES =
- DestDataset_ESRIASCIIGRID = D:\Raster_Outputs   # Destination Esri ASCII Grid Directory

Readers:
- ESRIASCIIGRID_1: ESRIASCIIGRID from $(SourceDataset_ESRIASCIIGRID) in BritishNatGrid

Writers:
- ESRIASCIIGRID_2: ESRIASCIIGRID to $(DestDataset_ESRIASCIIGRID) in BritishNatGrid

ESRIASCIIGRID (reader ESRIASCIIGRID_1)
    -> RasterMosaicker
RasterMosaicker
    NODATA_OVERWRITE = No
    MERGE_PALETTES_NAME = Yes
    SNAPPING_TYPE_NAME = Offset
    COMPOSITE_USING_ALPHA_BAND_NAME = No
    INTERPOLATION_TYPE_NAME = Nearest Neighbor
    ACCUM_ATTRS_NAME = No
    -> Terrain_50_DTM (writer ESRIASCIIGRID_2)
Terrain_50_DTM (writer ESRIASCIIGRID_2)
