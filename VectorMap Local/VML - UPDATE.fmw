FME workspace VML - UPDATE.fmw

Parameters:
- SourceDataset_OSVECTORMAPLOCAL = Q:\GIS_DATA\ZZ Original GIS Data\01 Ordnance Survey\VectorMap Local\2014-04-22\**\*.gz   # Source OS VectorMap Local File(s)
- SourceDataset_SHAPE = $(FME_MF_DIR)Symbols_and_Styles\VML_Points.shp   # Source of Line Symbol shapefiles (Directory)
- DestDataset_CSV = C:\TempData\test mastermap\outputs   # Destination for CSV files containing data that couldn't be joined/merged
- DestDataset_SHAPE = C:\TempData\vml\shapeout   # Destination Esri Shape Directory
- DestDataset_ORACLE8I_3 = co_gistest   # Destination Oracle Spatial Object Service

Readers:
- SHAPE_1: SHAPE from $(SourceDataset_SHAPE) in BritishNatGrid
- OSVECTORMAPLOCAL_1: OSVECTORMAPLOCAL from $(SourceDataset_OSVECTORMAPLOCAL) in BritishNatGrid

Writers:
- ORACLE8I_1: ORACLE8I to $(DestDataset_ORACLE8I_3) in BritishNatGrid
- SHAPE_2: SHAPE to $(DestDataset_SHAPE) in BritishNatGrid
- CSV_1: CSV to $(DestDataset_CSV)

Note: VML Loader / Created by Jonathan Moules / Version 6; 2013-07-25 / - Removed Line Joiners. They were breaking / Oracle (it couldn't handle the output and took / forever to do selections) / Version 5; 2013-07-18 / - Lots of data-quality checking. / - Updated to 2013. / Version 4 / Version 3; 6/9/12 / - Finds & Fixes bad Polygons that FME thinks / are good but that cause ArcGIS/ArcSDE issues. / Version 2; 4/9/12 / - Dissolves Areas across tiles / - Cleans up bad Areas / - dumped VML_ID / - Joins Lines and Road Centre Lines / Version 1; 5/3/12 / Full working version
Note: BenchMark / gistest - 15hrs / gislive - 8hrs

Bookmark: Text
Note: This bookmark is taken from the Cartographic Text / section of the MasterMap Loader
Text (reader OSVECTORMAPLOCAL_1)
    attributes: gml_id xml_buffer, featureCode xml_int16, featureDescription xml_char(43), textRendering.anchorPosition xml_int16, textRendering.font xml_int16, textRendering.height xml_real32, textRendering.orientation xml_int16, textString xml_buffer, anchorPoint xml_geometry
    -> AttributeRemover_4
AttributeRemover_4
    REMOVE_ATTRS = gml_id,anchorPoint
    -> AttributeRenamer
Note: Dump 1 character text "strings"
StringLengthCalculator
    SRC_ATTR = TEXTSTRING
    LENGTH_ATTR = _length
    -> Tester
Tester
    TEST_MODE = Automatic
    TEST_DESCRIPTION = ""
    BOOL_OP = OR
    TEST_CLAUSE = TEST @Value(_length) > 1
    PASSED -> CoordinateExtractor_2
Note: This is where the anchor point is
CoordinateExtractor_2
    Y_ATTR = _y_orig
    X_ATTR = _x_orig
    Z_DEFAULT = -9999
    Z_ATTR = _z
    IND = 0
    -> AttributeExposer
Note: A simple optimisation (smaller file space). / We only need two digits of precision.
CoordinateRounder_3
    ZPREC = 0
    YPREC = 2
    XPREC = 2
    ROUNDED -> AttributeRemover
Note: This bookmark takes the Text inputs - text string and anchor point, then creates / a line that GISs will use as the basis for text placement. / The line is correctly placed and rotated in relation to the anchor point.
AttributeRemover
    REMOVE_ATTRS = _length,_x_orig,_y_orig,_z,fme_rotation,fme_rotation_original,_xmax,_xmin,_x,_ymax,_ymin,_y,_zmax,_zmin,_y_mid,_x_mid,_x_offset,_y_offset
    -> Counter_4
Counter_4
    SCOPE = Local
    START = 1
    DOMAIN = counter
    CNT_ATTR = MI_PRINX
    -> vml_text (writer SHAPE_2)
    -> OSMM.OS_VML_TEXT (writer ORACLE8I_1)
OSMM.OS_VML_TEXT (writer ORACLE8I_1)
    attributes: FEATURE_CODE smallint, DESCRIPTION varchar2(50), ANCHOR_POSITION smallint, FONT smallint, HEIGHT float, ORIENTATION smallint, TEXTSTRING varchar2(250), MI_PRINX integer, MI_STYLE varchar2(250)
vml_text (writer SHAPE_2)
    attributes: FEATURE_CO number(6,0), DESCRIPTIO char(50), ANCHOR_POS number(6,0), FONT number(6,0), HEIGHT number(31,15), ORIENTATIO number(6,0), TEXTSTRING char(250), MI_PRINX number(11,0), MI_STYLE char(250)

Bookmark: Renamer
AttributeRenamer
    ATTR_LIST = ANCHOR_POSITION,textRendering.anchorPosition,FEATURE_CODE,featureCode,DESCRIPTION,featureDescription,FONT,textRendering.font,HEIGHT,textRendering.height,ORIENTATION,textRendering.orientation,TEXTSTRING,textString
    -> StringLengthCalculator

Bookmark: Pre-Rotation
Note: Get fme_rotation to / save an expression / on the supplied attribute
AttributeExposer
    ATTR_LIST = fme_rotation
    -> AttributeCopier
AttributeCopier
    ATTR_LIST = fme_rotation_original,fme_rotation
    -> AttributeSetter
Note: Force all text horizontal / to avoid issues
AttributeSetter
    VAL = 0
    DEST_ATTR = fme_rotation
    -> TextStroker_2

Bookmark: Create all bounds for text box
TextStroker_2
    OUTPUT_TYPE = Polygon features
    FONT_NAME = Arial
    TEXT_ATTRIBUTE = TEXTSTRING
    FONT_WIDTH_MULT = 1.0
    PADDING = 0
    STROKED -> BoundsExtractor
BoundsExtractor
    YMIN = _ymin
    ZMIN = _zmin
    XMIN = _xmin
    XMAX = _xmax
    ZMAX = _zmax
    YMAX = _ymax
    -> GeometryRemover
Note: Turns the text into text, then get's the co-ordinates / for a bounding box that would surround it / That includes not only max/min but also a mid point
GeometryRemover
    -> ExpressionEvaluator_6
ExpressionEvaluator_6
    VAL_ATTR = _y_mid
    EXPRESSION = @Value(_ymin) + ((@Value(_ymax) - @Value(_ymin)) / 2)
    -> ExpressionEvaluator_7
ExpressionEvaluator_7
    VAL_ATTR = _x_mid
    EXPRESSION = @Value(_xmin) + ((@Value(_xmax) - @Value(_xmin)) / 2)
    -> TestFilter_8

Bookmark: Eastings
TestFilter_8
    TEST_LIST = TEST_CLAUSE,"TEST @Value(ANCHOR_POSITION) = 0",TEST_LIST,"&ANCHOR_POSITION,=,0",TEST_MODE,Automatic,BOOL_OP,OR,BL,TEST_CLAUSE,"TEST @Value(ANCHOR_POSITION) = 1",TEST_LIST,"&ANCHOR_POSITION,=,1",TEST_MODE,Automatic,BOOL_OP,OR,ML,TEST_CLAUSE,"TEST @Value(ANCHOR_POSITION) = 2",TEST_LIST,"&ANCHOR_POSITION,=,2",TEST_MODE,Automatic,BOOL_OP,OR,TL,TEST_CLAUSE,"TEST @Value(ANCHOR_POSITION) = 3",TEST_LIST,"&ANCHOR_POSITION,=,3",TEST_MODE,Automatic,BOOL_OP,OR,BM,TEST_CLAUSE,"TEST @Value(ANCHOR_POSITION) = 4",TEST_LIST,"&ANCHOR_POSITION,=,4",TEST_MODE,Automatic,BOOL_OP,OR,Middle,TEST_CLAUSE,"TEST @Value(ANCHOR_POSITION) = 5",TEST_LIST,"&ANCHOR_POSITION,=,5",TEST_MODE,Automatic,BOOL_OP,OR,TM,TEST_CLAUSE,"TEST @Value(ANCHOR_POSITION) = 6",TEST_LIST,"&ANCHOR_POSITION,=,6",TEST_MODE,Automatic,BOOL_OP,OR,BR,TEST_CLAUSE,"TEST @Value(ANCHOR_POSITION) = 7",TEST_LIST,"&ANCHOR_POSITION,=,7",TEST_MODE,Automatic,BOOL_OP,OR,MR,TEST_CLAUSE,"TEST @Value(ANCHOR_POSITION) = 8",TEST_LIST,"&ANCHOR_POSITION,=,8",TEST_MODE,Automatic,BOOL_OP,OR,TR
    DEFAULT_VALUE = <UNFILTERED>
    BL -> AttributeCopier_9
    ML -> AttributeCopier_9
    TL -> AttributeCopier_9
    BM -> AttributeCopier_8
    TM -> AttributeCopier_8
    Middle -> AttributeCopier_8
    BR -> AttributeCopier_6
    MR -> AttributeCopier_6
    TR -> AttributeCopier_6
AttributeCopier_9
    ATTR_LIST = _x,_xmin
    -> TestFilter_6
AttributeCopier_8
    ATTR_LIST = _x,_x_mid
    -> TestFilter_6
AttributeCopier_6
    ATTR_LIST = _x,_xmax
    -> TestFilter_6

Bookmark: Northings
TestFilter_6
    TEST_LIST = TEST_CLAUSE,"TEST @Value(ANCHOR_POSITION) = 0",TEST_LIST,"&ANCHOR_POSITION,=,0",TEST_MODE,Automatic,BOOL_OP,OR,BL,TEST_CLAUSE,"TEST @Value(ANCHOR_POSITION) = 1",TEST_LIST,"&ANCHOR_POSITION,=,1",TEST_MODE,Automatic,BOOL_OP,OR,ML,TEST_CLAUSE,"TEST @Value(ANCHOR_POSITION) = 2",TEST_LIST,"&ANCHOR_POSITION,=,2",TEST_MODE,Automatic,BOOL_OP,OR,TL,TEST_CLAUSE,"TEST @Value(ANCHOR_POSITION) = 3",TEST_LIST,"&ANCHOR_POSITION,=,3",TEST_MODE,Automatic,BOOL_OP,OR,BM,TEST_CLAUSE,"TEST @Value(ANCHOR_POSITION) = 4",TEST_LIST,"&ANCHOR_POSITION,=,4",TEST_MODE,Automatic,BOOL_OP,OR,Middle,TEST_CLAUSE,"TEST @Value(ANCHOR_POSITION) = 5",TEST_LIST,"&ANCHOR_POSITION,=,5",TEST_MODE,Automatic,BOOL_OP,OR,TM,TEST_CLAUSE,"TEST @Value(ANCHOR_POSITION) = 6",TEST_LIST,"&ANCHOR_POSITION,=,6",TEST_MODE,Automatic,BOOL_OP,OR,BR,TEST_CLAUSE,"TEST @Value(ANCHOR_POSITION) = 7",TEST_LIST,"&ANCHOR_POSITION,=,7",TEST_MODE,Automatic,BOOL_OP,OR,MR,TEST_CLAUSE,"TEST @Value(ANCHOR_POSITION) = 8",TEST_LIST,"&ANCHOR_POSITION,=,8",TEST_MODE,Automatic,BOOL_OP,OR,TR
    DEFAULT_VALUE = <UNFILTERED>
    BL -> AttributeCopier_2
    BM -> AttributeCopier_2
    BR -> AttributeCopier_2
    TL -> AttributeCopier_5
    TM -> AttributeCopier_5
    TR -> AttributeCopier_5
    ML -> AttributeCopier_7
    Middle -> AttributeCopier_7
    MR -> AttributeCopier_7
AttributeCopier_2
    ATTR_LIST = _y,_ymin
    -> 2DPointReplacer
AttributeCopier_7
    ATTR_LIST = _y,_y_mid
    -> 2DPointReplacer
AttributeCopier_5
    ATTR_LIST = _y,_ymax
    -> 2DPointReplacer

Bookmark: Create line
2DPointReplacer
    XVALATTR = @Value(_xmin)
    YVALATTR = @Value(_y_mid)
    POINT -> 2DPointAdder
Note: The new line goes down the / vertical centre of the text / bounding box.
2DPointAdder
    XVALATTR = @Value(_xmax)
    YVALATTR = @Value(_y_mid)
    -> ExpressionEvaluator_8

Bookmark: Offset
ExpressionEvaluator_8
    VAL_ATTR = _x_offset
    EXPRESSION = @Value(_x_orig) - @Value(_x)
    -> ExpressionEvaluator_9
ExpressionEvaluator_9
    VAL_ATTR = _y_offset
    EXPRESSION = @Value(_y_orig) - @Value(_y)
    -> Offsetter_2
Note: Offset the line based on / where the AnchorPosition is.
Offsetter_2
    YOFF = @Value(_y_offset)
    ZOFF = 0
    XOFF = @Value(_x_offset)
    OFFSET -> Rotator_2

Bookmark: Rotation
Note: We rotate around the original / anchor point.
Rotator_2
    YORIG = @Value(_y_orig)
    ANGLE = @Value(fme_rotation_original)
    XORIG = @Value(_x_orig)
    ROTATED -> CoordinateRounder_3

Bookmark: Area
Area (reader OSVECTORMAPLOCAL_1)
    attributes: gml_id xml_buffer, featureCode xml_int16, featureDescription xml_char(43), polygon xml_geometry
    -> AttributeRemover_2
Note: Cleans Data
AttributeRemover_2
    REMOVE_ATTRS = gml_id,polygon
    -> AttributeRenamer_2
Note: Just in case something has been relegated / from a area to line/polygon. / That causes problems.
AttributeKeeper_4
    KEEP_ATTRS = FEATURE_CODE,DESCRIPTION
    -> Counter_2
Counter_2
    SCOPE = Local
    START = 1
    DOMAIN = counter
    CNT_ATTR = MI_PRINX
    -> area (writer SHAPE_2)
    -> OSMM.OS_VML_AREA (writer ORACLE8I_1)
OSMM.OS_VML_AREA (writer ORACLE8I_1)
    attributes: FEATURE_CODE smallint, DESCRIPTION varchar2(50), MI_PRINX integer, MI_STYLE varchar2(250)
area (writer SHAPE_2)
    attributes: FEATURE_CO number(6,0), DESCRIPTIO char(50), MI_PRINX number(11,0), MI_STYLE char(250)

Bookmark: Renamer
AttributeRenamer_2
    ATTR_LIST = FEATURE_CODE,featureCode,DESCRIPTION,featureDescription
    -> CoordinateRounder_2

Bookmark: Area Cleanup
Note: Bad data with bad coordinates / doesn't dissolve
Note: Unfortunately, VML is very bad data. Its topologically unsound, it only comes in tiles and / those don't even necessarily align. / To resolve this we have to do several things: / (a) Round coordinates to 0 decimal places so things do align. / (b) Clean up the resultant spikes and topological mess that results (Snapper does this; we aren't using it for snapping) / (c) Deaggregate any polygons that were aggregated (typically as a result of (a+b)). / (d) Dump data that is still so bad that it will cause the translation to fail if it hits the Dissolver. / (e) Dissolve the polygons across tiles together using Feature ID.
CoordinateRounder_2
    ZPREC = 0
    YPREC = 0
    XPREC = 0
    ROUNDED -> Snapper_2
Snapper_2
    SNAPTYPE_PARAM = Vertex Snapping
    SAVE_SHORT_LINES = No
    TOLERANCE = 0
    EXTEND_LINES = NEVER
    SNAPPED -> Deaggregator_2
    UNTOUCHED -> Deaggregator_2
Deaggregator_2
    LIST_ATTR_MODE_LOOKUP = LEAN
    MODE = Flatten All Levels
    SPLIT_COMPOSITES = No
    EXPLODE_INSTANCES = No
    DEAGGREGATED -> Dissolver_2
Dissolver_2
    GROUP_BY = FEATURE_CODE
    NO_OVRLP = No
    ACCUM_INPUT_ATTRS = Yes
    AREA -> SpikeRemover

Bookmark: Clear Up
SpikeRemover
    SPIKEANGLE = 5
    UNCHANGED -> GeometryValidator_2
    CHANGED -> GeometryValidator_2
Note: Final Clean Up
GeometryValidator_2
    SHELL_VALIDATION = SHELL_VALIDATION
    CHECK_HOLE_TOUCHING_POLYGON = No
    DUP_COORDS_CHECK_Z = Yes
    NULL_REMOVAL = NULL_REMOVAL
    TYPE_REPAIR = TYPE_REPAIR
    SELF_INTERSECTING = SELF_INTERSECTING
    PRESETS = All
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = Yes
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> GeometryValidator_3
    REPAIRED -> GeometryValidator_3
Note: Dump Bad Data
GeometryValidator_3
    SHELL_VALIDATION = SHELL_VALIDATION
    CHECK_HOLE_TOUCHING_POLYGON = No
    DUP_COORDS_CHECK_Z = Yes
    NULL_REMOVAL = NULL_REMOVAL
    TYPE_REPAIR = TYPE_REPAIR
    SELF_INTERSECTING = SELF_INTERSECTING
    PRESETS = All
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = No
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> GeometryFilter_2
GeometryFilter_2
    GEOM_PORT_NAMES = Area
    BREAK_AGG = No
    AREA -> AttributeKeeper_4

Bookmark: Line
Line (reader OSVECTORMAPLOCAL_1)
    attributes: gml_id xml_buffer, featureCode xml_int16, featureDescription xml_char(43), polyline xml_geometry
    -> AttributeRemover_3
AttributeRemover_3
    REMOVE_ATTRS = gml_id,polyline
    -> AttributeRenamer_3
Note: Final Clean Up
GeometryValidator_4
    SHELL_VALIDATION = SHELL_VALIDATION
    CHECK_HOLE_TOUCHING_POLYGON = No
    DUP_COORDS_CHECK_Z = Yes
    NULL_REMOVAL = NULL_REMOVAL
    TYPE_REPAIR = TYPE_REPAIR
    SELF_INTERSECTING = SELF_INTERSECTING
    PRESETS = All
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = Yes
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> GeometryValidator_5
    REPAIRED -> GeometryValidator_5
Note: Dump Bad Data
GeometryValidator_5
    SHELL_VALIDATION = SHELL_VALIDATION
    CHECK_HOLE_TOUCHING_POLYGON = No
    DUP_COORDS_CHECK_Z = Yes
    NULL_REMOVAL = NULL_REMOVAL
    TYPE_REPAIR = TYPE_REPAIR
    SELF_INTERSECTING = SELF_INTERSECTING
    PRESETS = All
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = No
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> Counter_3
Counter_3
    SCOPE = Local
    START = 1
    DOMAIN = counter
    CNT_ATTR = MI_PRINX
    -> line (writer SHAPE_2)
    -> OSMM.OS_VML_LINE (writer ORACLE8I_1)
OSMM.OS_VML_LINE (writer ORACLE8I_1)
    attributes: FEATURE_CODE smallint, DESCRIPTION varchar2(50), MI_PRINX integer, MI_STYLE varchar2(250)
line (writer SHAPE_2)
    attributes: FEATURE_CO number(6,0), DESCRIPTIO char(50), MI_PRINX number(11,0), MI_STYLE char(250)

Bookmark: Renamer
AttributeRenamer_3
    ATTR_LIST = FEATURE_CODE,featureCode,DESCRIPTION,featureDescription
    -> GeometryValidator_4

Bookmark: Road Centre Lines
RoadCLine (reader OSVECTORMAPLOCAL_1)
    attributes: gml_id xml_buffer, featureCode xml_int16, featureDescription xml_char(43), roadNumber xml_buffer, roadName xml_buffer, polyline xml_geometry
    -> AttributeRemover_5
AttributeRemover_5
    REMOVE_ATTRS = gml_id,polyline
    -> AttributeRenamer_4
Note: Final Clean Up
GeometryValidator_6
    SHELL_VALIDATION = SHELL_VALIDATION
    CHECK_HOLE_TOUCHING_POLYGON = No
    DUP_COORDS_CHECK_Z = Yes
    NULL_REMOVAL = NULL_REMOVAL
    TYPE_REPAIR = TYPE_REPAIR
    SELF_INTERSECTING = SELF_INTERSECTING
    PRESETS = All
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = Yes
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> GeometryValidator_7
    REPAIRED -> GeometryValidator_7
Note: Dump Bad Data
GeometryValidator_7
    SHELL_VALIDATION = SHELL_VALIDATION
    CHECK_HOLE_TOUCHING_POLYGON = No
    DUP_COORDS_CHECK_Z = Yes
    NULL_REMOVAL = NULL_REMOVAL
    TYPE_REPAIR = TYPE_REPAIR
    SELF_INTERSECTING = SELF_INTERSECTING
    PRESETS = All
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = No
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> Counter_5
Counter_5
    SCOPE = Local
    START = 1
    DOMAIN = counter
    CNT_ATTR = MI_PRINX
    -> roads (writer SHAPE_2)
    -> OSMM.OS_VML_ROADCENTRELINE (writer ORACLE8I_1)
OSMM.OS_VML_ROADCENTRELINE (writer ORACLE8I_1)
    attributes: FEATURE_CODE smallint, DESCRIPTION varchar2(50), ROAD_NUMBER varchar2(15), ROAD_NAME varchar2(150), MI_PRINX integer, MI_STYLE varchar2(250)
roads (writer SHAPE_2)
    attributes: FEATURE_CO number(6,0), DESCRIPTIO char(50), ROAD_NUMBE char(15), ROAD_NAME char(150), MI_PRINX number(11,0), MI_STYLE char(250)

Bookmark: Renamer
AttributeRenamer_4
    ATTR_LIST = FEATURE_CODE,featureCode,DESCRIPTION,featureDescription,ROAD_NUMBER,roadNumber,ROAD_NAME,roadName
    -> GeometryValidator_6

Bookmark: Points
VectorMapPoint (reader OSVECTORMAPLOCAL_1)
    attributes: gml_id xml_buffer, featureCode xml_int16, featureDescription xml_char(43), orientation xml_int16, point xml_geometry
    -> CoordinateExtractor
Note: We'll need to know where this point is / to do the line symbol offset properly.
Note: Most of this bookmark copied from the / MasterMap Loader
CoordinateExtractor
    Y_ATTR = _y_orig
    X_ATTR = _x_orig
    Z_DEFAULT = -9999
    IND = 0
    -> FeatureMerger [input 1]

Bookmark: Line Symbology Prep
Note: Line symbology is imported / from a shapefile.
VML_Points (reader SHAPE_1)
    attributes: style_desc char(30), feat_code number(9,0)
    -> BoundsExtractor_2

Bookmark: Get symbol anchor co-ordinates
Note: The line symbols are fairly randomly drawn, / with the starting/ending vertex possibly being anywhere. / Also they're scattered all over the Midlands.
Note: These anchors are later used to ensure the symbol is placed in exactly / the right place. They're also used for rotation.
BoundsExtractor_2
    YMIN = _ymin
    ZMIN = _zmin
    XMIN = _xmin
    XMAX = _xmax
    ZMAX = _zmax
    YMAX = _ymax
    -> ExpressionEvaluator_3
AttributeKeeper
    KEEP_ATTRS = feat_code,_x_anchor,_y_anchor
    -> GeometryExtractor

Bookmark: x anchor
ExpressionEvaluator_3
    VAL_ATTR = _x_anchor
    EXPRESSION = @Value(_xmin) + ((@Value(_xmax)-@Value(_xmin)) /2 )
    -> ExpressionEvaluator_4

Bookmark: y anchor
ExpressionEvaluator_4
    VAL_ATTR = _y_anchor
    EXPRESSION = @Value(_ymin)+((@Value(_ymax)-@Value(_ymin))/2)
    -> AttributeKeeper

Bookmark: Symbol Geometry extraction
GeometryExtractor
    ATTR = _geometry
    KIND_LONG = FME Binary
    -> GeometryRemover_2
GeometryRemover_2
    -> FeatureMerger [input 2]

Bookmark: Point to Line Conversion
Note: Join the point with the correct line symbol. / While "Joiner" transformer would be faster, / it is also more effort to maintain as it / requires a wizard to use. / Also we need to get FME to do a bit of prep / on the supplier data. Easier this way.
FeatureMerger
    BUILD_INCOMPLETE = No
    PROCESS_DUPS = No
    MERGE_TYPE = Attributes Only
    REFERATTR = featureCode
    REFEEATTR = feat_code
    COMPLETE -> GeometryReplacer
    INCOMPLETE -> No Point to Line Conversion (writer CSV_1)
Note: Point needs to be converted from points to line symbols.
Note: Replace the point with / the new line symbol
Note: Using the anchor points calculated / earlier, these transformers move the / geometry to the correct location.
GeometryReplacer
    ATTR = _geometry
    KIND_LONG = FME Binary
    -> ExpressionEvaluator

Bookmark: Offsetting
ExpressionEvaluator
    VAL_ATTR = _x_offset
    EXPRESSION = (@Value(_x_orig)-@Value(_x_anchor))
    -> ExpressionEvaluator_2
ExpressionEvaluator_2
    VAL_ATTR = _y_offset
    EXPRESSION = (@Value(_y_orig)-@Value(_y_anchor))
    -> Offsetter
Offsetter
    YOFF = @Value(_y_offset)
    ZOFF = 0
    XOFF = @Value(_x_offset)
    OFFSET -> AttributeRenamer_5

Bookmark: Renamer
AttributeRenamer_5
    ATTR_LIST = FEATURE_CODE,featureCode,DESCRIPTION,featureDescription,ORIENTATION,orientation
    -> ExpressionEvaluator_5

Bookmark: Rotation
ExpressionEvaluator_5
    VAL_ATTR = _rotation
    EXPRESSION = @Value(ORIENTATION) / 10
    -> Rotator
Note: Rotate the symbol around the anchor. / The OS provide the orientation in tenths / of a degree.
Rotator
    YORIG = @Value(_y_orig)
    ANGLE = @Value(_rotation)
    XORIG = @Value(_x_orig)
    ROTATED -> CoordinateRounder

Bookmark: VML Point
Note: Remove input-dataset attributes we don't want
Note: A simple optimisation (smaller file space). / We only need two digits of precision / (not even that really).
CoordinateRounder
    ZPREC = 0
    YPREC = 2
    XPREC = 2
    ROUNDED -> AttributeRemover_11
Note: Remove FME-generated / attributes we don't want
AttributeRemover_11
    REMOVE_ATTRS = gml_id,point,_x_orig,_y_orig,feat_code,_x_anchor,_y_anchor,_geometry,_x_offset,_y_offset,_rotation
    -> Counter_6
Counter_6
    SCOPE = Local
    START = 1
    DOMAIN = counter
    CNT_ATTR = MI_PRINX
    -> points (writer SHAPE_2)
    -> OSMM.OS_VML_POINT (writer ORACLE8I_1)
OSMM.OS_VML_POINT (writer ORACLE8I_1)
    attributes: FEATURE_CODE smallint, DESCRIPTION varchar2(50), ORIENTATION smallint, MI_PRINX integer, MI_STYLE varchar2(250)
points (writer SHAPE_2)
    attributes: FEATURE_CO number(6,0), DESCRIPTIO char(50), ORIENTATIO number(6,0), MI_PRINX number(11,0), MI_STYLE char(250)

Bookmark: Line-less data
Note: No Point to Line Conversion
No Point to Line Conversion (writer CSV_1)
    attributes: gml_id char(254), featureCode number(6,0), featureDescription char(43), orientation number(6,0), point char(254)

Bookmark: Reposition text in relation to anchor point
Note: The OS use an attribute called "anchorPosition" which tells us where the text should be in relation to the anchor point. / FME uses a fixed bottom-left anchor point, so we need to move our text in relation to that. / These Filters figure out where we're moving to.
