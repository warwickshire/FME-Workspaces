FME workspace OSMM_style_lookup_concatenator-creates join csv.fmw

Parameters:
- DestDataset_CSV = \\wcc-corp.ad\BuData\SICM\05 Workstreams\Observatory\09 GIS\01 Spatial Data Management\GIS FME Loaders\01 Oracle FME Loaders\01 Ordnance Survey (OS) data\OS MasterMap\Symbols   # Destination Comma Separated Value (CSV) Directory
- SourceDataset_XLS_ADO = H:\sicm\05 Workstreams\Observatory\09 GIS\01 Spatial Data Management\GIS FME Loaders\01 Oracle FME Loaders\01 Ordnance Survey (OS) data\OS MasterMap\Symbols\osmm_style_lookup_v15.xls   # Source Microsoft Excel File(s)
- DestDataset_XLS_ADO = C:\TempData\OS Sample data\re-ordered.xls   # Destination Microsoft Excel File

Readers:
- XLS_ADO_1: XLS_ADO from $(SourceDataset_XLS_ADO)

Writers:
- CSV_1: CSV to $(DestDataset_CSV)
- XLS_ADO_2: XLS_ADO to $(DestDataset_XLS_ADO)

NewFeatureType (reader XLS_ADO_1)
    attributes: featureType varchar(255), OSMMSTYLE_NAME varchar(255), MI_STYLE varchar(255), descriptiveGroup varchar(255), descriptiveTerm varchar(255), physicalPresence varchar(255), make varchar(255), Notes-First join varchar(255), Notes-Second Join varchar(255)
    -> Tester
StringConcatenator_6
    PARM_LINE = @Value(featureType)@Value(descriptiveGroup)@Value(descriptiveTerm)@Value(make)@Value(physicalPresence)
    VAL_ATTR = join_key
    -> AttributeKeeper
AttributeKeeper
    KEEP_ATTRS = MI_STYLE,OSMMSTYLE_NAME,join_key
    -> osmmStyle_names_join_table (writer CSV_1)
osmmStyle_names_join_table (writer CSV_1)
    attributes: join_key char(150), OSMMSTYLE_NAME char(100), MI_STYLE char(100)
Note: USE THIS to re-order desc term and desc group in the excel file itself.
reordered_set (writer XLS_ADO_2) [off]
    attributes: featureType varchar(255), OSMMSTYLE_NAME varchar(255), MI_STYLE varchar(255), descriptiveGroup varchar(255), descriptiveTerm varchar(255), physicalPresence varchar(255), make varchar(255), Notes_First join varchar(255), Notes_Second Join varchar(255)

Bookmark: DescriptiveGroup
Note: Some input data has multiple DescriptiveTerm entries. / This sorts them to alphabetical
Note: Splits if there is more than one Descriptive Term
Tester
    TEST_MODE = Automatic
    TEST_DESCRIPTION = ""
    BOOL_OP = OR
    TEST_LIST = &descriptiveTerm,CONTAINS,,
    TEST_CLAUSE = TEST "@Value(descriptiveGroup)" CONTAINS ","
    PASSED -> AttributeSplitter
    FAILED -> ListKeeper_2
AttributeSplitter
    LIST_NAME = _list
    ATTR_NAME = descriptiveGroup
    DELIMITER = ,
    TRIM_OPTION = Both
    DROP_EMPTY_PARTS = No
    -> ListSorter
ListSorter
    TYPE = Alphabetic
    SRC_LIST = _list{}
    ORDER = Increasing
    -> ListConcatenator
ListConcatenator
    VAL_ATTR = descriptiveGroup
    SEP = ,
    LIST_ATTR = _list{}
    DROP_EMPTY_PARTS = No
    -> ListKeeper_2
ListKeeper_2
    -> Tester_2

Bookmark: DescriptiveTerm
Note: Some input data has multiple DescriptiveTerm entries. / This sorts them to alphabetical
Note: Splits if there is more than one Descriptive Term
Tester_2
    TEST_MODE = Automatic
    TEST_DESCRIPTION = ""
    BOOL_OP = OR
    TEST_LIST = &descriptiveTerm,CONTAINS,,
    TEST_CLAUSE = TEST "@Value(descriptiveTerm)" CONTAINS ","
    PASSED -> AttributeSplitter_2
    FAILED -> ListKeeper_3
AttributeSplitter_2
    LIST_NAME = _list
    ATTR_NAME = descriptiveTerm
    DELIMITER = ,
    TRIM_OPTION = Both
    DROP_EMPTY_PARTS = No
    -> ListSorter_2
ListSorter_2
    TYPE = Alphabetic
    SRC_LIST = _list{}
    ORDER = Increasing
    -> ListConcatenator_2
ListConcatenator_2
    VAL_ATTR = descriptiveTerm
    SEP = ,
    LIST_ATTR = _list{}
    DROP_EMPTY_PARTS = No
    -> ListKeeper_3
ListKeeper_3
    -> StringConcatenator_6
    -> reordered_set (writer XLS_ADO_2)
