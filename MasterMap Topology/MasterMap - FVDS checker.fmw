FME workspace MasterMap - FVDS checker.fmw

Parameters:
- SourceDataset_CSV = Q:\GIS_DATA\ZZ Original GIS Data\01 Ordnance Survey\OS MasterMap\COUs\1500120 - COU14 for 87198 - New Warwickshire Live Load - 2month COU\fv\*.gz   # Source Comma Separated Value (CSV) File(s)
- FEATURE_TYPES =
- DestDataset_CSV = C:\TempData\test mastermap\outputs   # Destination for CSV files containing data that couldn't be joined/merged

Readers:
- CSV_1: CSV from $(SourceDataset_CSV) in BritishNatGrid

Writers:
- CSV_2: CSV to $(DestDataset_CSV)

Note: HOW TO USE / ------------------- / 1) Change the SQL in SQLCreator to point at the right OSMM tables / 2) Change input CSV reader to point at FVDS directory (*.gz filetype) / 3) Run / 4) Check outputs to make sure everything passed the test. / !!!!WARNING!!!! / This workspace uses a LOT of RAM (14GB for 4.2million features). / Free as much RAM as you can before starting! / Make sure you run this with 64bit FME. / !!!!WARNING!!!!
Note: FVDS checker / Created by Jonathan Moules / Version 2 - 18/4/12 - Fully working version / Version 1 - 18/4/12 - Basics in place
Note: FVDS / col0 = OS_ID / col1 = Version / col2 = Version Date (don't want)
Note: Benchmarks / ----------------- / 4.3 million features / RAM Use: ~14GB / Time: ~17mins / 28.8million features: / RAM Use: ~3/5ths Physical RAM / Temp Disk Use: ~25GB / Time: ~4hrs 8mins
Note: FVDS (Feature Validation DataSet) / The FVDS is an Ordnance Survey CSV file that contains a list of all / TOIDS and their versions. It's designed to ensure that OSMM holdings / are valid and current. / This runs a complete comparison between the FVDS dataset and / the full holdings in the database. / Anything that appears in only one or the other is outputted to the / appropriate CSV file. Also anything that has a non-matching version / is also output to a CSV file. / This version is RAM intensive as it reads in both datasets entirely before / comparing. / A less RAM intensive but probably slower and more complicated / comparitive method may be possible.
87245-FV000001-10 (reader CSV_1)
    attributes: col0 number(17,0), col1 number(4,0), col2 char(11)
    -> StringLengthCalculator
Note: Prepend "osgb" to TOID
StringConcatenator
    PARM_LINE = osgb@Value(col0)
    VAL_ATTR = col0
    -> FeatureMerger [input 1]
Note: Core Checking!
FeatureMerger
    BUILD_INCOMPLETE = No
    PROCESS_DUPS = No
    MERGE_TYPE = Attributes Only
    REFERATTR = col0
    REFEEATTR = OS_ID
    COMPLETE -> Tester_2
    INCOMPLETE -> In FVDS only (writer CSV_2)
    UNREFERENCED -> In Database only (writer CSV_2)
Note: Everything is in both tables, / but does the version match? / Failed = No.
Tester_2
    TEST_MODE = Automatic
    TEST_DESCRIPTION = ""
    BOOL_OP = OR
    TEST_CLAUSE = NUM_TEST "@Value(VERSION)" = "@Value(col1)"
    FAILED -> In Both but no matching version (writer CSV_2)

Bookmark: Padding for TOIDS
Note: The OS provide FVDS data with TOIDS that are missing / their leading 0's. This fixes that by pre-fixing with padding.
StringLengthCalculator
    SRC_ATTR = col0
    LENGTH_ATTR = _length
    -> Tester
Tester
    TEST_MODE = Automatic
    TEST_DESCRIPTION = ""
    BOOL_OP = OR
    TEST_CLAUSE = TEST "@Value(_length)" >= "16"
    FAILED -> StringFormatter
    PASSED -> AttributeRemover
StringFormatter
    SRC_ATTRS = col0
    FORMAT = 016s
    -> AttributeRemover
AttributeRemover
    REMOVE_ATTRS = _length
    -> StringConcatenator

Bookmark: SQL
Note: Database Data is loaded from here. / Change tables referenced as applicable.
SQLCreator
    ORACLE8I_DB_USER_NAME = OSMM
    ORACLE8I_DB_PASSWORD = osmmpass
    SQL_STATEMENT = SELECT OS_ID, VERSION FROM OS_MM_BOUNDARYLINE Union All SELECT OS_ID, VERSION FROM OS_MM_CARTOGRAPHIC_SYMBOL Union All SELECT OS_ID, VERSION FROM OS_MM_CARTOGRAPHIC_TEXT Union All SELECT OS_ID, VERSION FROM OS_MM_TOPOGRAPHIC_POINT Union All SELECT OS_ID, VERSION FROM OS_MM_TOPOGRAPHIC_LINE Union All Select Os_Id, Version From OS_MM_TOPOGRAPHIC_AREA
    EXPOSED_ATTRIBUTE_LIST = OS_ID,VERSION
    ORACLE8I_DB_SERVER_TYPE = ORACLE8i
    DATASET = co_gistest
    ORACLE8I_DB_REMOVE_SCHEMA_QUALIFIER = NO
    FORMAT = ORACLE8I_DB
    RESULT -> FeatureMerger [input 2]

Bookmark: Bad Data
In Both but no matching version (writer CSV_2)
    attributes: DB_OS_ID char(16), DB_VERSION number(4,0), FVDS_OS_ID char(16), FVDS_VERSION number(4,0)
In FVDS only (writer CSV_2)
    attributes: OS_ID char(16), VERSION number(4,0)
In Database only (writer CSV_2)
    attributes: OS_ID char(16), VERSION number(4,0)
