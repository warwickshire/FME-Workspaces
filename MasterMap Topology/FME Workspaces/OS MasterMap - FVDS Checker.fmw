FME workspace OS MasterMap - FVDS Checker.fmw
Title: FVDS Checker
Description: See FVDS Checker - Readme.txt
Usage: See FVDS Checker - Readme.txt
Requirements: FME 2012 SP2 or later
Legal terms conditions: Copyright 2012, Warwickshire County Council.
Released under the Creative Commons Attribution-NonCommercial-ShareAlike 3.0 Unported license
We waive the NonCommercial limitation for all PSMA and OSMA members.

Parameters:
- Source_MasterMap_Data =   # Source FVDS (Directory|File)
- Destination_FAILED_FVDS =   # Directory for CSV files of failed TOIDS
- Source_Oracle_Server =   # Oracle Server
- Oracle_username =   # Oracle Username
- Oracle_password =   # Oracle Password

Readers:
- CSV_1: CSV from $(Source_MasterMap_Data) in BritishNatGrid

Writers:
- CSV_2: CSV to $(Destination_FAILED_FVDS)

Note: IMPORTANT / -------------------------- / See included Readme file for information / about this workspace, including how to use it.
Note: Created by Jonathan Moules / Warwickshire County Council / 2012. / Based on Version 2 of the FVDS checker
Note: FVDS / col0 = OS_ID / col1 = Version / col2 = Version Date (don't want)
87245-FV000001-10 (reader CSV_1)
    attributes: col0 number(17,0), col1 number(4,0), col2 char(11)
    -> StringLengthCalculator
Note: Benchmarks / ----------------- / 4.3 million features / RAM Use: ~14GB / Time: ~17mins / 28.8million features: / RAM Use: ~3/5ths Physical RAM / Temp Disk Use: ~25GB / Time: ~4hrs 8mins
StringLengthCalculator
    SRC_ATTR = col0
    LENGTH_ATTR = _length
    -> Tester
Note: FVDS (Feature Validation DataSet) / The FVDS is an Ordnance Survey CSV file that contains a list of all / TOIDS and their versions. It's designed to ensure that OSMM holdings / are valid and current. / This runs a complete comparison between the FVDS dataset and / the full holdings in the database. / Anything that appears in only one or the other is outputted to the / appropriate CSV file. Also anything that has a non-matching version / is also output to a CSV file. / This version is RAM intensive as it reads in both datasets entirely before / comparing. / A less RAM intensive but probably slower and more complicated / comparitive method may be possible.
Tester
    TEST_DESCRIPTION = ""
    TEST_CLAUSE = TEST "@Value(_length)" >= "16"
    BOOL_OP = OR
    TEST_MODE = Automatic
    FAILED -> StringFormatter
    PASSED -> AttributeRemover
StringFormatter
    FORMAT = 016s
    SRC_ATTRS = col0
    -> AttributeRemover
AttributeRemover
    REMOVE_ATTRS = _length
    -> StringConcatenator
Note: Prepend "osgb" to TOID
StringConcatenator
    PARM_LINE = osgb@Value(col0)
    VAL_ATTR = col0
    -> FeatureMerger [input 1]
Note: Database Data is loaded from here. / Change tables referenced as applicable.
SQLCreator
    ORACLE8I_DB_REMOVE_SCHEMA_QUALIFIER = NO
    FORMAT = ORACLE8I_DB
    DATASET = $(Source_Oracle_Server)
    SQL_STATEMENT = SELECT OS_ID, VERSION FROM OS_MM_BOUNDARYLINE Union All SELECT OS_ID, VERSION FROM OS_MM_CARTOGRAPHIC_SYMBOL Union All SELECT OS_ID, VERSION FROM OS_MM_CARTOGRAPHIC_TEXT Union All SELECT OS_ID, VERSION FROM OS_MM_TOPOGRAPHIC_POINT Union All SELECT OS_ID, VERSION FROM OS_MM_TOPOGRAPHIC_LINE Union All Select Os_Id, Version From OS_MM_TOPOGRAPHIC_AREA
    ORACLE8I_DB_USER_NAME = $(Oracle_username)
    EXPOSED_ATTRIBUTE_LIST = OS_ID,VERSION
    ORACLE8I_DB_SERVER_TYPE = ORACLE8i
    ORACLE8I_DB_PASSWORD = $(Oracle_password)
    RESULT -> FeatureMerger [input 2]
Note: Core Checking!
FeatureMerger
    REFEEATTR = OS_ID
    MERGE_TYPE = Attributes Only
    PROCESS_DUPS = No
    BUILD_INCOMPLETE = No
    REFERATTR = col0
    COMPLETE -> Tester_2
    INCOMPLETE -> In FVDS only (writer CSV_2)
    UNREFERENCED -> In Database only (writer CSV_2)
Note: Everything is in both tables, / but does the version match? / Failed = No.
Tester_2
    TEST_DESCRIPTION = ""
    TEST_CLAUSE = NUM_TEST "@Value(VERSION)" = "@Value(col1)"
    BOOL_OP = OR
    TEST_MODE = Automatic
    FAILED -> In Both but no matching version (writer CSV_2)
In Both but no matching version (writer CSV_2)
    attributes: DB_OS_ID char(16), DB_VERSION number(4,0), FVDS_OS_ID char(16), FVDS_VERSION number(4,0)
In FVDS only (writer CSV_2)
    attributes: OS_ID char(16), VERSION number(4,0)
In Database only (writer CSV_2)
    attributes: OS_ID char(16), VERSION number(4,0)

Bookmark: Padding for TOIDS
Note: The OS provide FVDS data with TOIDS that are missing / their leading 0's. This fixes that by pre-fixing with padding.
