FME workspace MasterMap - Full Supply - to SpatiaLite.fmw

Parameters:
- SourceDataset_SHAPE = ""\\wcc-corp.ad\BuData\SICM\05 Workstreams\Observatory\09 GIS\01 Spatial Data Management\GIS FME Loaders\01 Oracle FME Loaders\01 Ordnance Survey (OS) data\OS MasterMap\Symbols\OSMMCartoSymbol symbols.shp" "\\wcc-corp.ad\BuData\SICM\05 Workstreams\Observatory\09 GIS\01 Spatial Data Management\GIS FME Loaders\01 Oracle FME Loaders\01 Ordnance Survey (OS) data\OS MasterMap\Symbols\OSMMTopoPoint symbols.shp""   # Source of Line Symbol shapefiles (Directory)
- SourceDataset_DNF_3 = Q:\GIS_DATA\ZZ Original GIS Data\Ordnance Survey\OS MasterMap\FULL SUPPLIES\86700_55048 - ORIGINAL Supply - Conwy Property - 6month COU\01\*.gz   # Source OS (GB) MasterMap File(s)
- DestDataset_CSV = C:\TempData\test mastermap\outputs   # Destination for CSV files containing data that couldn't be joined/merged
- DestDataset_SPATIALITE = C:\TempData\outputs\conwy_spatialite.sl3   # Destination Spatialite Database(s)

Readers:
- SHAPE_1: SHAPE from $(SourceDataset_SHAPE) in BritishNatGrid
- DNF_1: DNF from $(SourceDataset_DNF_3) in BritishNatGrid

Writers:
- SPATIALITE_1: SPATIALITE to $(DestDataset_SPATIALITE) in BritishNatGrid
- CSV_1: CSV to $(DestDataset_CSV)

TopographicArea (reader DNF_1)
    attributes: TOID xml_char(16), FeatureCode xml_int16, Version xml_int16, VersionDate xml_char(10), Theme xml_char(64), ThemeCount xml_int16, CalculatedAreaValue xml_real64, ChangeDate xml_char(10), ReasonForChange xml_char(36), ChangeHistory{}.ChangeDate xml_char(10), ChangeHistory{}.ReasonForChange xml_char(36), ChangeHistoryCount xml_int16, DescriptiveGroup xml_char(254), DescriptiveGroupCount xml_int16, DescriptiveTerm xml_char(254), DescriptiveTermCount xml_int16, Make xml_char(12), PhysicalLevel xml_int16, PhysicalPresence xml_char(16), broken xml_char(5), DirectedNode.NegativeOrientation.GradeSeparation xml_int32, BoundedBy xml_char(64), DeletionDate xml_char(10), ChangesSinceDate xml_char(10), VehicleQualifier{}.Load.For xml_char(64), PostalAddress.WelshAddress.PostTown xml_char(30), LensFocalLength xml_char(64), AddressStatus.StructureType xml_char(18), AliasAddress{}.WelshAlternative xml_char(50), NdrAddress.Firm xml_char(50),
      ReferenceToOrganisationKey xml_int32, DerivedFromAerialPhoto{}.FrameNumber xml_int16, DateTimeQualifier{}.DayCount xml_int16, AddressAuthority.NDR_UARN xml_char(50), AliasAddress.WelshAlternative xml_char(50), VehicleQualifier{}.MaxCompositeHeight.Inches xml_real64, DateTimeQualifier{}.NamedDateCount xml_int16, HeightAboveGroundLevel xml_real64, CreatedBy xml_char(254), DerivedFromAerialPhotoCount xml_int16, AlternativeAddress.DependentThoroughfare xml_char(80), Bs7666Address.Locality xml_char(80), AliasAddress.OrganisationDescription xml_char(50), AccuracyOfPosition xml_char(7), VehicleQualifier{}.Use.ForCount xml_int16, FlyingHeight xml_real64, NominalImageScale xml_char(64), ReferenceToITN{} xml_char(16), AliasAddress{}.OrganisationAtResidential xml_char(50), Bs7666Address.PostCode xml_char(8), VehicleQualifier{}.Use.ExceptFor xml_char(64), Bs7666Address.AdminArea xml_char(100), FrameNumber xml_int16, TruePOBoxAddress.POBox xml_char(6), PostalAddress.WelshAddress.Thoroughfare xml_char(80), ChunkingPolicy xml_char(64), VehicleQualifier{}.Use.ExceptForCount xml_int16, AccuracyOfHeightAboveDatum xml_char(7), Length xml_real64, Orientation xml_int16,
      VehicleQualifier{}.Load.ForCount xml_int16, Resolution xml_real64, Film xml_char(64), AlternativeAddress.Thoroughfare xml_char(80), LensFocalLengthCount xml_int16, AccuracyOfHeightAboveGroundLevel xml_char(7), PostalAddress.Thoroughfare xml_char(80), ReferenceToTopographicArea{} xml_char(16), ClassificationConfidence xml_int32, HeightAboveDatum xml_real64, AliasAddress.BuildingName xml_char(50), FlightLine xml_int16, AliasAddress{}.AlsoKnownAs xml_char(50), DateTimeQualifier{}.NamedDate xml_char(64), VehicleQualifier{}.MaxCompositeHeight.Feet xml_real64, AddressStatus.MatchStatus xml_char(37), PostalAddress.PostCode.Type xml_char(5), NatureOfRoad xml_char(31), DirectedLink xml_char(16), Aircraft xml_char(64), ReferenceToCartographicText xml_char(16), AliasAddressCount xml_int32, AlternativeAddress.BuildingNumber xml_int32, geometryIsComplete xml_boolean, ReferenceToNode.Orientation xml_char(1), ThemeList xml_char(254), ReferenceToFeature{} xml_char(16), StructureType xml_char(18), TruePOBoxAddress.PostCode xml_char(8), EnvironmentQualifier{}.ClassificationCount xml_int16,
      SubsectionDistance{} xml_real64, Font xml_decimal(3,0), AnchorPosition xml_decimal(3,0), LaCode xml_int32, FilmId xml_char(10), dateFlown xml_char(64), ReferenceToNetwork{} xml_char(16), Bs7666Address.Saon xml_char(110), DateTimeQualifier{}.NamedTimeCount xml_int16, NominalImageScaleCount xml_int16, KmReference xml_char(6), DistanceFromStart xml_real64, PositionalQuality xml_char(11), ReferenceToPathLink xml_char(16), AliasAddress{}.TradingName xml_char(50), PathNameCount xml_int16, PostalAddress.BuildingNumber xml_int32, ReferenceToAddress xml_char(16), queryChangeSinceDate xml_char(10), DateFlownCount xml_int16, Bs7666Address.Paon xml_char(200), ReferenceToUDPRN xml_int32, PostalAddress.PlotNumber xml_char(64), VehicleQualifier{}.Type.For xml_char(64), Bs7666Address.Town xml_char(60), ReferenceToRoad xml_char(16), ReferenceToRoadNode.GradeSeparation xml_int32, VehicleQualifier{}.Load.ExceptForCount xml_int16, AddressAuthority.UDPRN xml_int32, PostalAddress.Department xml_char(60),
      VehicleQualifier{}.Type.ExceptForCount xml_int16, FileSize xml_real64, ReferenceToAddressKey xml_int32, PhysicalStatus xml_char(10), PostalAddress.DoubleDependentLocality xml_char(35), LensSerialNumber xml_char(64), Copyright xml_char(64), OSAPR xml_char(20), DirectedLink{}.Orientation xml_char(1), PathName xml_char(64), ReferenceToNode xml_char(16), ChunkSize xml_real64, PostalAddress.AddressId.AddressKey xml_int32, ReferenceToRoadNode.Orientation xml_char(1), dateFlownCount xml_int16, FlownBy xml_char(15), DerivedFromAerialPhoto{}.FilmId xml_char(10), PostalAddress.WelshAddress.DependentThoroughfare xml_char(80), MatchStatus xml_char(37), DateTimeQualifier{}.NamedPeriod xml_char(64), GeometryFormat xml_char(64), PostalAddress.BuildingName xml_char(50), PostalAddressDate xml_char(10), Bs7666Address.Street xml_char(80), DateTimeQualifier{}.TimeRange{}.StartTime xml_char(8), ReferenceToLink xml_char(16), PostalAddress.PostCode xml_char(8), AliasAddress{}.OrganisationDescription xml_char(50), AddressAuthority.UMRRN xml_int32, PostalAddress.DependentLocality xml_char(35),
      PostalAddress.DependentThoroughfare xml_char(80), ReferenceToRoadLink.Version xml_int32, AddressAuthority.CT_UARN xml_char(50), NominalFlyingHeight xml_char(64), SubsectionPoint{} xml_char(64), PostalAddress.SubBuildingName xml_char(30), AddressStatus.PositionalQuality.Accuracy xml_char(20), AddressStatus.PhysicalStatus xml_char(10), LandUseGroup xml_char(4), PostalAddress.POBox xml_char(6), DateTimeQualifier{}.TimeRange{}.EndTime xml_char(8), ReasonForDeparture xml_char(7), Camera xml_char(64), PDescCode xml_char(5), MultipleOccupancyCount xml_int16, BaseFunction xml_char(120), ReferenceToFeature xml_char(16), ReferenceToNode.GradeSeparation xml_int32, PositionalQuality.Accuracy xml_char(20), DateOfCompletion xml_char(10), TextString xml_char(254), NonBoundingLine xml_boolean, VehicleQualifier{}.Use.For xml_char(64), SupplyType xml_char(64), CreatedByCount xml_int16, DirectedLink.Orientation xml_char(1), AddressStatus.PositionalQuality xml_char(11), TruePOBoxAddress.NonGeographic xml_boolean, AliasAddress{}.Department xml_char(50), CorrectionType xml_char(14),
      ReferenceToRoadLink xml_char(16), ReferenceToOSAPR xml_char(20), ThemeListCount xml_int16, ReferenceToAddress.Version xml_int32, DateTimeQualifier{}.DateRange{}.StartDate xml_char(10), EnvironmentQualifier{}.Classification xml_char(64), xml_rotation xml_real64, PostalAddress.PostTown xml_char(30), Height xml_real32, DirectedLink{} xml_char(16), AliasAddress.OrganisationAtResidential xml_char(50), AlternativeAddress.SubBuildingName xml_char(30), DirectedNode.PositiveOrientation xml_char(16), AlternativeAddress.BuildingName xml_char(50), DirectedNode.PositiveOrientation.GradeSeparation xml_int32, RoadName xml_char(64), TruePOBoxAddress.GeographicAddress xml_char(325), VehicleQualifier{}.Type.ForCount xml_int16, ReferenceToRoad.Version xml_int32, ReferenceToTopographicFeature.Version xml_int32, PostalAddress.WelshAddress.DependentLocality xml_char(35), DirectedNode.NegativeOrientation xml_char(16), JunctionName xml_char(64), NewBuildFlag xml_boolean, AliasAddress.AlsoKnownAs xml_char(50), VehicleQualifier{}.Load.ExceptFor xml_char(64), PostalAddress.Organisation xml_char(60), AliasAddress.Department xml_char(50), PostalAddress.AddressId.OrganisationKey xml_int32, VehicleQualifier{}.MaxHeight xml_real64,
      DateTimeQualifier{}.NamedTime xml_char(64), SCatCode xml_char(4), AliasAddress.TradingName xml_char(50), ReferenceToRoadNode xml_char(16), AliasAddress{}.BuildingName xml_char(50), PostalAddress.DeliveryPointSuffix xml_char(2), ReferenceToCartographicText.Version xml_int32, NominalFlyingHeightCount xml_int16, PostalAddress.NonGeographic xml_boolean, VehicleQualifier{}.Type.ExceptFor xml_char(64), Control xml_char(27), NetworkMember{} xml_char(16), TruePOBoxAddress.Organisation xml_char(60), DateTimeQualifier{}.DateRange{}.EndDate xml_char(10), EnvironmentQualifier{}.Instruction xml_char(20), RoadNameCount xml_int16, DateTimeQualifier{}.Day xml_char(64), DateFlown xml_char(64), PostalAddress.WelshAddress.DoubleDependentLocality xml_char(35), ReferenceToTopographicFeature xml_char(16)
    -> AttributeKeeper_2
Note: [optimisation] Dump junk.
AttributeKeeper_2
    KEEP_LIST = ChangeHistory{}
    KEEP_ATTRS = TOID,FeatureCode,Version,VersionDate,Theme,DescriptiveGroup,DescriptiveTerm,Make,PhysicalLevel,PhysicalPresence,HeightAboveGroundLevel,AccuracyOfPosition,AccuracyOfHeightAboveDatum,Orientation,AccuracyOfHeightAboveGroundLevel,HeightAboveDatum,Font,AnchorPosition,TextString,NonBoundingLine,Height
    -> FeatureTypeExtractor
FeatureTypeExtractor
    DEST_ATTR = _feature_type
    -> StringConcatenator
Note: Prepend "osgb" to TOID
StringConcatenator
    PARM_LINE = osgb@Value(TOID)
    VAL_ATTR = TOID
    -> AttributeCreator_4
Note: For the Change History
AttributeCreator_4
    ATTR_LIST = Change_Hist_String,"",Last_Change_Date,
    -> ListAccumulator_5
Note: Loop through a list and convert it to a concatenated string
ListAccumulator_5: ListAttributeAccumulator
    LIST_NAME = ChangeHistory{}
    -> AttributeRemover_2
Note: Benchmarks / -------------------------- / 18797 features: / Time: ~50 secs / 194,476 features: / Time: ~7.5 mins / 4.3million features / Time: / 28.8million features / Time: ~3.5 days / RAM:
Note: HOW TO USE / -------------------------- / 1) Change OSMM Reader to point to right directory. / 2) Change writers to points at desired tables. / 3) Run.
Note: MasterMap Loader / Created by Jonathan Moules / Version 22; 6/6/2012 ~ 1hr / Fixed bug where was joining wrong Symbols / DescriptiveGroup is now ordered like DescriptiveText / Version 21; 18/4/2012 ~2mins / Updated to prepend 'osgb' to TOIDS / Version 20; 16/4/2012 ~30mins / Updated to FME 2012 / Version 19; 13/2/12; ~4hrs / Cartographic text now uses the AnchorPosition / attribute correctly. / Version 18; 10/1/2012; ~4hrs / Third finished working version. / Added Version & Version Date - for use with COUs / Added MI_STYLE data to joined stylesheet. / Version 17; 6/1/12; 1.25 days. / Now incorporates OSMMSTYLE_NAME joining. / -This uses a custom spreadsheet which took most / of the time for this version. / Version 16; 30/12/11 / Second finished working version / Version 15; 30/12/11 / Further Tidying up. / Issues with lists further investigated. / ListAccumulator issues resolved. / Works in 2011 again. / Version 14; 29/12/11 / Further refactoring. / Issues with FME's handling of lists discovered. / ListAccumulator problems / Works in 2012 or later only. / Version 13; 23/12/11 / Started refactoring workspace to use one / dynamic input. Means less duplicate transformers / Version 12; 23/12/11 / First Finished Version / Topo Point converted to Lines. / Everything enabled. / Version 11; 22/12/11 / Carto Symbol converted to lines. / Version 10; Nov 2011 / Tidied up / Version 9; Oct 2011 / Version 8; Oct/2011 / Work on Cartographic Text. / Converted to FME 2011 friendly.
AttributeRemover_2
    LIST_ATTRS = ChangeHistory{}
    REMOVE_ATTRS = ChangeDate,ReasonForChange
    -> Tester_3
Note: Splits if there is more than one DescriptiveGroup
Tester_3
    TEST_MODE = Automatic
    TEST_DESCRIPTION = ""
    BOOL_OP = OR
    TEST_LIST = &DescriptiveTerm,CONTAINS,,
    TEST_CLAUSE = TEST "@Value(DescriptiveGroup)" CONTAINS ","
    PASSED -> AttributeSplitter_2
    FAILED -> ListKeeper_3
AttributeSplitter_2
    LIST_NAME = _list
    ATTR_NAME = DescriptiveGroup
    DELIMITER = ,
    TRIM_OPTION = Both
    DROP_EMPTY_PARTS = No
    -> ListSorter_2
ListSorter_2
    TYPE = Alphabetic
    SRC_LIST = _list{}
    ORDER = Increasing
    -> ListConcatenator_2
ListConcatenator_2
    VAL_ATTR = DescriptiveGroup
    SEP = ,
    LIST_ATTR = _list{}
    DROP_EMPTY_PARTS = No
    -> ListKeeper_3
ListKeeper_3
    -> FeatureTypeFilter_2
FeatureTypeFilter_2
    ATTRIBUTES = TopographicArea,TopographicPoint,TopographicLine,BoundaryLine,CartographicText,CartographicSymbol
    TopographicArea -> Tester
    TopographicLine -> StringConcatenator_4
    CartographicText -> StringConcatenator_2
    CartographicSymbol -> StringConcatenator_2
    BoundaryLine -> StringConcatenator_4
    TopographicPoint -> StringConcatenator_3
Note: Splits if there is more than one Descriptive Term
Tester
    TEST_MODE = Automatic
    BOOL_OP = OR
    TEST_LIST = &DescriptiveTerm,CONTAINS,,
    TEST_CLAUSE = TEST @Value(DescriptiveTerm) CONTAINS ,
    PASSED -> AttributeSplitter
    FAILED -> ListKeeper_2
AttributeSplitter
    LIST_NAME = _list
    ATTR_NAME = DescriptiveTerm
    DELIMITER = ,
    TRIM_OPTION = Both
    DROP_EMPTY_PARTS = No
    -> ListSorter
ListSorter
    TYPE = Alphabetic
    SRC_LIST = _list{}
    ORDER = Increasing
    -> ListConcatenator
ListConcatenator
    VAL_ATTR = DescriptiveTerm
    SEP = ,
    LIST_ATTR = _list{}
    DROP_EMPTY_PARTS = No
    -> ListKeeper_2
ListKeeper_2
    -> StringConcatenator_5
StringConcatenator_5
    PARM_LINE = @Value(_feature_type)@Value(DescriptiveGroup)@Value(DescriptiveTerm)@Value(Make)
    VAL_ATTR = _concatenated
    -> Joiner
StringConcatenator_3
    PARM_LINE = @Value(_feature_type)@Value(DescriptiveGroup)@Value(DescriptiveTerm)@Value(Make)
    VAL_ATTR = _concatenated
    -> Joiner
StringConcatenator_4
    PARM_LINE = @Value(_feature_type)@Value(DescriptiveGroup)@Value(DescriptiveTerm)@Value(Make)@Value(PhysicalPresence)
    VAL_ATTR = _concatenated
    -> Joiner
StringConcatenator_2
    PARM_LINE = @Value(_feature_type)@Value(DescriptiveGroup)@Value(DescriptiveTerm)
    VAL_ATTR = _concatenated
    -> Joiner
Note: [optimisation] I conducted a speed test between / Joiner and FeatureMerger for this function using / a 4.29 million feature dataset. / Joiner: 1hr 45mins / FeatureMerger: 2hrs 58minutes
Joiner
    USE_SSPI = No
    __WB_CARDINALITY = 1:0..1+
    __WB_DIRECTIVES = SEPARATOR,"(,)",DUPLICATE_DELIMS,no,SKIP_FOOTER,0,SKIP_LINES,1,FIELD_NAMES,YES,FIELD_NAMES_AFTER_HEADER,no,SCAN_MAX_FEATURES,0,STRIP_QUOTES,yes,MERGE_SCHEMAS,YES
    __WB_ADDED_FIELDS = MI_STYLE,OSMMSTYLE_NAME
    __WB_SERVER_TYPE = CSV
    __WB_CACHE_SIZE = 5000
    __WB_ODBC_TABLE = osmmStyle_names_join_table
    __WB_ODBC_SOURCE = \\wcc-corp.ad\BuData\SICM\05 Workstreams\Observatory\09 GIS\01 Spatial Data Management\GIS FME Loaders\01 Oracle FME Loaders\01 Ordnance Survey (OS) data\OS MasterMap\Symbols\osmmStyle_names_join_table.csv
    __WB_TABLE_FIELDS = join_key,OSMMSTYLE_NAME,MI_STYLE
    __WB_KEY_FIELDS = join_key,_concatenated
    __WB_TRIM_KEYS = Yes
    JOINED -> Tester_2
Tester_2
    TEST_MODE = Automatic
    BOOL_OP = OR
    TEST_LIST = &_matched_records,=,1
    TEST_CLAUSE = TEST @Value(_matched_records) = 1
    FAILED -> AttributeCreator
    PASSED -> AttributeRemover_9
AttributeCreator
    ATTR_LIST = OSMMSTYLE_NAME,unknownFill
    -> No matching OSMM Styles (writer CSV_1)
    -> AttributeRemover_9
Note: Get rid of attributes used for / FeatureMerger join.
AttributeRemover_9
    REMOVE_ATTRS = _concatenated,_matched_records
    -> FeatureTypeFilter
Note: [optimisation] Because of the way the filter works, / we want the types that have most features / at the top.
FeatureTypeFilter
    ATTRIBUTES = TopographicLine,TopographicArea,CartographicText,BoundaryLine,CartographicSymbol,TopographicPoint
    TopographicLine -> AttributeRemover_7
    TopographicArea -> AttributeRemover_5
    CartographicText -> AttributeRemover_4
    BoundaryLine -> AttributeRemover_3
    CartographicSymbol -> CoordinateExtractor
    TopographicPoint -> CoordinateExtractor
AttributeRemover_7
    REMOVE_ATTRS = AccuracyOfHeightAboveDatum,AccuracyOfHeightAboveGroundLevel,AnchorPosition,Font,Height,HeightAboveDatum,HeightAboveGroundLevel,Orientation,TextString,_feature_type
    -> AttributeRenamer_3
AttributeRenamer_3
    ATTR_LIST = CHANGE_HISTORY,Change_Hist_String,DESCRIPTIVE_GROUP,DescriptiveGroup,DESCRIPTIVE_TERM,DescriptiveTerm,FEATURE_CODE,FeatureCode,MAKE,Make,OS_ID,TOID,THEME,Theme,LAST_CHANGE_DATE,Last_Change_Date,SURFACE_LEVEL,PhysicalLevel,PHYSICAL_PRESENCE,PhysicalPresence,NON_POLYGON_LINE,NonBoundingLine,ACCURACY_OF_POSITION,AccuracyOfPosition,VERSION,Version,VERSION_DATE,VersionDate
    -> Counter_3
Counter_3
    SCOPE = Local
    START = 1
    DOMAIN = counter
    CNT_ATTR = MI_PRINX
    -> os_mm_topographic_line (writer SPATIALITE_1)
os_mm_topographic_line (writer SPATIALITE_1)
    attributes: os_id string(20), feature_code integer, theme string(64), descriptive_group string(40), descriptive_term string(40), make string(12), surface_level integer, physical_presence string(16), accuracy_of_position string(7), non_polygon_line string(8), change_history string(1024), last_change_date date, osmmstyle_name string(70), version integer, version_date date, mi_prinx integer, mi_style string(255)
AttributeRemover_5
    REMOVE_ATTRS = AccuracyOfHeightAboveDatum,AccuracyOfHeightAboveGroundLevel,AccuracyOfPosition,AnchorPosition,Font,Height,HeightAboveDatum,HeightAboveGroundLevel,NonBoundingLine,Orientation,PhysicalLevel,PhysicalPresence,TextString,_feature_type
    -> AttributeRenamer_2
AttributeRenamer_2
    ATTR_LIST = CHANGE_HISTORY,Change_Hist_String,DESCRIPTIVE_GROUP,DescriptiveGroup,DESCRIPTIVE_TERM,DescriptiveTerm,FEATURE_CODE,FeatureCode,MAKE,Make,OS_ID,TOID,THEME,Theme,LAST_CHANGE_DATE,Last_Change_Date,VERSION,Version,VERSION_DATE,VersionDate
    -> Counter
Counter
    SCOPE = Local
    START = 1
    DOMAIN = counter
    CNT_ATTR = MI_PRINX
    -> os_mm_topographic_area (writer SPATIALITE_1)
os_mm_topographic_area (writer SPATIALITE_1)
    attributes: os_id string(20), feature_code integer, theme string(64), descriptive_group string(40), descriptive_term string(40), make string(12), change_history string(1024), last_change_date date, osmmstyle_name string(70), version integer, version_date date, mi_prinx integer, mi_style string(255)
AttributeRemover_4
    REMOVE_ATTRS = AccuracyOfHeightAboveDatum,AccuracyOfHeightAboveGroundLevel,AccuracyOfPosition,HeightAboveDatum,HeightAboveGroundLevel,NonBoundingLine,PhysicalPresence,_feature_type
    -> AttributeRenamer
AttributeRenamer
    ATTR_LIST = ANCHOR_POSITION,AnchorPosition,CHANGE_HISTORY,Change_Hist_String,DESCRIPTIVE_GROUP,DescriptiveGroup,DESCRIPTIVE_TERM,DescriptiveTerm,FEATURE_CODE,FeatureCode,FONT,Font,HEIGHT,Height,MAKE,Make,ORIENTATION,Orientation,SURFACE_LEVEL,PhysicalLevel,OS_ID,TOID,TEXTSTRING,TextString,THEME,Theme,LAST_CHANGE_DATE,Last_Change_Date,VERSION,Version,VERSION_DATE,VersionDate
    -> CoordinateExtractor_2
Note: This is where the anchor point is
CoordinateExtractor_2
    Y_ATTR = _y_orig
    X_ATTR = _x_orig
    Z_DEFAULT = -9999
    Z_ATTR = _z
    IND = 0
    -> AttributeExposer
Note: Get fme_rotation to / save an expression / on the supplied attribute
AttributeExposer
    ATTR_LIST = fme_rotation
    -> AttributeCopier
AttributeCopier
    ATTR_LIST = fme_rotation_original,fme_rotation
    -> AttributeSetter
Note: Force all text horizontal / to avoid issues
AttributeSetter
    VAL = 0
    DEST_ATTR = fme_rotation
    -> TextStroker_2
TextStroker_2
    OUTPUT_TYPE = Polygon features
    FONT_NAME = Arial
    TEXT_ATTRIBUTE = TEXTSTRING
    FONT_WIDTH_MULT = 1.0
    PADDING = 0
    STROKED -> BoundsExtractor
BoundsExtractor
    YMIN = _ymin
    ZMIN = _zmin
    XMIN = _xmin
    XMAX = _xmax
    ZMAX = _zmax
    YMAX = _ymax
    -> GeometryRemover
GeometryRemover
    -> ExpressionEvaluator_11
ExpressionEvaluator_11
    VAL_ATTR = _x_mid
    EXPRESSION = @Value(_xmin) + ((@Value(_xmax) - @Value(_xmin)) / 2)
    -> ExpressionEvaluator_5
ExpressionEvaluator_5
    VAL_ATTR = _y_mid
    EXPRESSION = @Value(_ymin) + ((@Value(_ymax) - @Value(_ymin)) / 2)
    -> TestFilter_8
TestFilter_8
    TEST_LIST = TEST_CLAUSE,"TEST @Value(ANCHOR_POSITION) = 0",TEST_LIST,"&ANCHOR_POSITION,=,0",TEST_MODE,Automatic,BOOL_OP,OR,BL,TEST_CLAUSE,"TEST @Value(ANCHOR_POSITION) = 1",TEST_LIST,"&ANCHOR_POSITION,=,1",TEST_MODE,Automatic,BOOL_OP,OR,ML,TEST_CLAUSE,"TEST @Value(ANCHOR_POSITION) = 2",TEST_LIST,"&ANCHOR_POSITION,=,2",TEST_MODE,Automatic,BOOL_OP,OR,TL,TEST_CLAUSE,"TEST @Value(ANCHOR_POSITION) = 3",TEST_LIST,"&ANCHOR_POSITION,=,3",TEST_MODE,Automatic,BOOL_OP,OR,BM,TEST_CLAUSE,"TEST @Value(ANCHOR_POSITION) = 4",TEST_LIST,"&ANCHOR_POSITION,=,4",TEST_MODE,Automatic,BOOL_OP,OR,Middle,TEST_CLAUSE,"TEST @Value(ANCHOR_POSITION) = 5",TEST_LIST,"&ANCHOR_POSITION,=,5",TEST_MODE,Automatic,BOOL_OP,OR,TM,TEST_CLAUSE,"TEST @Value(ANCHOR_POSITION) = 6",TEST_LIST,"&ANCHOR_POSITION,=,6",TEST_MODE,Automatic,BOOL_OP,OR,BR,TEST_CLAUSE,"TEST @Value(ANCHOR_POSITION) = 7",TEST_LIST,"&ANCHOR_POSITION,=,7",TEST_MODE,Automatic,BOOL_OP,OR,MR,TEST_CLAUSE,"TEST @Value(ANCHOR_POSITION) = 8",TEST_LIST,"&ANCHOR_POSITION,=,8",TEST_MODE,Automatic,BOOL_OP,OR,TR
    BL -> AttributeCopier_9
    ML -> AttributeCopier_9
    TL -> AttributeCopier_9
    BM -> AttributeCopier_8
    TM -> AttributeCopier_8
    Middle -> AttributeCopier_8
    BR -> AttributeCopier_6
    MR -> AttributeCopier_6
    TR -> AttributeCopier_6
AttributeCopier_9
    ATTR_LIST = _x,_xmin
    -> TestFilter_6
AttributeCopier_8
    ATTR_LIST = _x,_x_mid
    -> TestFilter_6
AttributeCopier_6
    ATTR_LIST = _x,_xmax
    -> TestFilter_6
TestFilter_6
    TEST_LIST = TEST_CLAUSE,"TEST @Value(ANCHOR_POSITION) = 0",TEST_LIST,"&ANCHOR_POSITION,=,0",TEST_MODE,Automatic,BOOL_OP,OR,BL,TEST_CLAUSE,"TEST @Value(ANCHOR_POSITION) = 1",TEST_LIST,"&ANCHOR_POSITION,=,1",TEST_MODE,Automatic,BOOL_OP,OR,ML,TEST_CLAUSE,"TEST @Value(ANCHOR_POSITION) = 2",TEST_LIST,"&ANCHOR_POSITION,=,2",TEST_MODE,Automatic,BOOL_OP,OR,TL,TEST_CLAUSE,"TEST @Value(ANCHOR_POSITION) = 3",TEST_LIST,"&ANCHOR_POSITION,=,3",TEST_MODE,Automatic,BOOL_OP,OR,BM,TEST_CLAUSE,"TEST @Value(ANCHOR_POSITION) = 4",TEST_LIST,"&ANCHOR_POSITION,=,4",TEST_MODE,Automatic,BOOL_OP,OR,Middle,TEST_CLAUSE,"TEST @Value(ANCHOR_POSITION) = 5",TEST_LIST,"&ANCHOR_POSITION,=,5",TEST_MODE,Automatic,BOOL_OP,OR,TM,TEST_CLAUSE,"TEST @Value(ANCHOR_POSITION) = 6",TEST_LIST,"&ANCHOR_POSITION,=,6",TEST_MODE,Automatic,BOOL_OP,OR,BR,TEST_CLAUSE,"TEST @Value(ANCHOR_POSITION) = 7",TEST_LIST,"&ANCHOR_POSITION,=,7",TEST_MODE,Automatic,BOOL_OP,OR,MR,TEST_CLAUSE,"TEST @Value(ANCHOR_POSITION) = 8",TEST_LIST,"&ANCHOR_POSITION,=,8",TEST_MODE,Automatic,BOOL_OP,OR,TR
    BL -> AttributeCopier_2
    BM -> AttributeCopier_2
    BR -> AttributeCopier_2
    TL -> AttributeCopier_5
    TM -> AttributeCopier_5
    TR -> AttributeCopier_5
    ML -> AttributeCopier_7
    Middle -> AttributeCopier_7
    MR -> AttributeCopier_7
AttributeCopier_2
    ATTR_LIST = _y,_ymin
    -> 2DPointReplacer
AttributeCopier_7
    ATTR_LIST = _y,_y_mid
    -> 2DPointReplacer
AttributeCopier_5
    ATTR_LIST = _y,_ymax
    -> 2DPointReplacer
2DPointReplacer
    XVALATTR = @Value(_xmin)
    YVALATTR = @Value(_y_mid)
    POINT -> 2DPointAdder_2
2DPointAdder_2
    XVALATTR = @Value(_xmax)
    YVALATTR = @Value(_y_mid)
    -> ExpressionEvaluator_6
ExpressionEvaluator_6
    VAL_ATTR = _x_offset
    EXPRESSION = @Value(_x_orig) - @Value(_x)
    -> ExpressionEvaluator_7
ExpressionEvaluator_7
    VAL_ATTR = _y_offset
    EXPRESSION = @Value(_y_orig) - @Value(_y)
    -> Offsetter_2
Offsetter_2
    YOFF = @Value(_y_offset)
    ZOFF = 0
    XOFF = @Value(_x_offset)
    OFFSET -> Rotator_2
Note: We rotate around the original / anchor point.
Rotator_2
    YORIG = @Value(_y_orig)
    ANGLE = @Value(fme_rotation_original)
    XORIG = @Value(_x_orig)
    ROTATED -> CoordinateRounder_5
Note: [optimisation] (smaller file space). / We only need two digits of precision / (not even that really).
CoordinateRounder_5
    ZPREC = 0
    YPREC = 2
    XPREC = 2
    ROUNDED -> AttributeRemover
AttributeRemover
    REMOVE_ATTRS = _x_orig,_y_orig,_z,fme_rotation,fme_rotation_original,_xmax,_xmin,_x,_ymax,_ymin,_y,_zmax,_zmin,_y_mid,_x_mid,_x_offset,_y_offset
    -> Counter_4
Counter_4
    SCOPE = Local
    START = 1
    DOMAIN = counter
    CNT_ATTR = MI_PRINX
    -> os_mm_cartographic_text (writer SPATIALITE_1)
os_mm_cartographic_text (writer SPATIALITE_1)
    attributes: os_id string(20), feature_code integer, theme string(64), descriptive_group string(40), descriptive_term string(40), make string(12), surface_level integer, anchor_position integer, font integer, height integer, orientation integer, textstring string(254), change_history string(1024), last_change_date date, osmmstyle_name string(70), version integer, version_date date, mi_prinx integer, mi_style string(254)
AttributeRemover_3
    REMOVE_ATTRS = AccuracyOfHeightAboveDatum,AccuracyOfHeightAboveGroundLevel,AnchorPosition,Font,Height,HeightAboveDatum,HeightAboveGroundLevel,Make,NonBoundingLine,Orientation,PhysicalLevel,PhysicalPresence,TextString,_feature_type
    -> AttributeRenamer_4
AttributeRenamer_4
    ATTR_LIST = CHANGE_HISTORY,Change_Hist_String,DESCRIPTIVE_GROUP,DescriptiveGroup,DESCRIPTIVE_TERM,DescriptiveTerm,FEATURE_CODE,FeatureCode,OS_ID,TOID,THEME,Theme,LAST_CHANGE_DATE,Last_Change_Date,ACCURACY_OF_POSITION,AccuracyOfPosition,VERSION,Version,VERSION_DATE,VersionDate
    -> Counter_5
Counter_5
    SCOPE = Local
    START = 1
    DOMAIN = counter
    CNT_ATTR = MI_PRINX
    -> os_mm_boundaryline (writer SPATIALITE_1)
os_mm_boundaryline (writer SPATIALITE_1)
    attributes: os_id string(20), feature_code integer, theme string(64), accuracy_of_position string(7), descriptive_group string(40), descriptive_term string(40), change_history string(1024), last_change_date date, osmmstyle_name string(70), version integer, version_date date, mi_prinx integer, mi_style string(255)
Note: We'll need to know where this point is / to do the line symbol offset properly.
CoordinateExtractor
    Y_ATTR = _y_orig
    X_ATTR = _x_orig
    Z_DEFAULT = -9999
    IND = 0
    -> FeatureMerger [input 1]
Note: No matching OSMM Styles
No matching OSMM Styles (writer CSV_1)
    attributes: _concatenated char(100), _feature_type char(20), DescriptiveGroup char(20), DescriptiveTerm char(50), Make char(20), PhysicalPresence char(20), TOID char(20), FeatureCode char(20), AnchorPosition char(20), PhysicalLevel char(20), AccuracyOfHeightAboveDatum char(20), Change_Hist_String char(20), Orientation char(20), HeightAboveDatum char(20), AccuracyOfPosition char(20), AccuracyOfHeightAboveGroundLevel char(20), NonBoundingLine char(20), HeightAboveGroundLevel char(20), Font char(20), TextString char(20), Last_Change_Date char(20), Height char(20), Theme char(20)
Note: Line symbology is imported / from a shapefile.
OSMMCartoSymbol symbols (reader SHAPE_1)
    attributes: feat_code char(6), stylename char(30), style_num number(4,0), centroid char(10)
    -> BoundsExtractor_2
BoundsExtractor_2
    YMIN = _ymin
    ZMIN = _zmin
    XMIN = _xmin
    XMAX = _xmax
    ZMAX = _zmax
    YMAX = _ymax
    -> TestFilter
TestFilter
    TEST_LIST = TEST_CLAUSE,"TEST @Value(centroid) = left",TEST_LIST,"&centroid,=,left",TEST_MODE,Automatic,BOOL_OP,OR,left
    left -> AttributeCopier_3
    <UNFILTERED> -> ExpressionEvaluator_2
AttributeCopier_3
    ATTR_LIST = _x_anchor,_xmin
    -> TestFilter_2
ExpressionEvaluator_2
    VAL_ATTR = _x_anchor
    EXPRESSION = @Value(_xmin) + ((@Value(_xmax)-@Value(_xmin)) /2 )
    -> TestFilter_2
TestFilter_2
    TEST_LIST = TEST_CLAUSE,"STRING_TEST @Value(centroid) = bottom",TEST_LIST,"&centroid,=,bottom",TEST_MODE,String,BOOL_OP,OR,bottom
    bottom -> AttributeCopier_4
    <UNFILTERED> -> ExpressionEvaluator_3
AttributeCopier_4
    ATTR_LIST = _y_anchor,_ymin
    -> AttributeKeeper
ExpressionEvaluator_3
    VAL_ATTR = _y_anchor
    EXPRESSION = @Value(_ymin)+((@Value(_ymax)-@Value(_ymin))/2)
    -> AttributeKeeper
AttributeKeeper
    KEEP_ATTRS = _x_anchor,_y_anchor,stylename
    -> GeometryExtractor
GeometryExtractor
    ATTR = _geometry
    OMIT_NAMESPACES_DISPLAY = No
    KIND_LONG = FME Binary
    -> GeometryRemover_2
GeometryRemover_2
    -> FeatureMerger [input 2]
Note: Join the point with the correct line symbol. / While "Joiner" transformer would be faster, / it is also more effort to maintain as it / requires a wizard to use. / Also we need to get FME to do a bit of prep / on the supplier data. Easier this way.
FeatureMerger
    BUILD_INCOMPLETE = No
    PROCESS_DUPS = No
    MERGE_TYPE = Attributes Only
    REFERATTR = OSMMSTYLE_NAME
    REFEEATTR = stylename
    COMPLETE -> GeometryReplacer
    INCOMPLETE -> No Point to Line Conversion (writer CSV_1)
Note: Replace the point with / the new line symbol
GeometryReplacer
    SRS_AXIS_ORDER_DISPLAY = Automatic
    ATTR = _geometry
    KIND_LONG = FME Binary
    -> ExpressionEvaluator_10
ExpressionEvaluator_10
    VAL_ATTR = _x_offset
    EXPRESSION = (@Value(_x_orig)-@Value(_x_anchor))
    -> ExpressionEvaluator
ExpressionEvaluator
    VAL_ATTR = _y_offset
    EXPRESSION = (@Value(_y_orig)-@Value(_y_anchor))
    -> Offsetter
Offsetter
    YOFF = @Value(_y_offset)
    ZOFF = 0
    XOFF = @Value(_x_offset)
    OFFSET -> TestFilter_4
TestFilter_4
    TEST_LIST = BOOL_OP,OR,COMPOSITE_TEST,<Unused>,TEST_CLAUSE,"TEST ""@Value(_feature_type)"" = ""CartographicSymbol""",Carto Symbol,BOOL_OP,OR,COMPOSITE_TEST,<Unused>,TEST_CLAUSE,"TEST ""@Value(_feature_type)"" = ""TopographicPoint""",Topo Point
    Topo Point -> AttributeRemover_15
    Carto Symbol -> AttributeRemover_12
Note: Remove input-dataset attributes we don't want
AttributeRemover_12
    REMOVE_ATTRS = AccuracyOfHeightAboveDatum,AccuracyOfHeightAboveGroundLevel,AccuracyOfPosition,AnchorPosition,Font,Height,HeightAboveDatum,HeightAboveGroundLevel,Make,NonBoundingLine,PhysicalPresence,TextString,_feature_type
    -> AttributeRenamer_5
AttributeRenamer_5
    ATTR_LIST = CHANGE_HISTORY,Change_Hist_String,DESCRIPTIVE_GROUP,DescriptiveGroup,DESCRIPTIVE_TERM,DescriptiveTerm,FEATURE_CODE,FeatureCode,OS_ID,TOID,THEME,Theme,LAST_CHANGE_DATE,Last_Change_Date,SURFACE_LEVEL,PhysicalLevel,ORIENTATION,Orientation,VERSION,Version,VERSION_DATE,VersionDate
    -> ExpressionEvaluator_4
ExpressionEvaluator_4
    VAL_ATTR = _rotation
    EXPRESSION = @Value(ORIENTATION) / 10
    -> Rotator
Rotator
    YORIG = @Value(_y_orig)
    ANGLE = @Value(_rotation)
    XORIG = @Value(_x_orig)
    ROTATED -> CoordinateRounder_2
Note: [optimisation] (smaller file space). / We only need two digits of precision / (not even that really).
CoordinateRounder_2
    ZPREC = 0
    YPREC = 2
    XPREC = 2
    ROUNDED -> AttributeRemover_11
Note: Remove FME-generated / attributes we don't want
AttributeRemover_11
    REMOVE_ATTRS = _x_orig,_y_orig,_x_anchor,_y_anchor,stylename,_geometry,_x_offset,_y_offset,_rotation
    -> Counter_6
Counter_6
    SCOPE = Local
    START = 1
    DOMAIN = counter
    CNT_ATTR = MI_PRINX
    -> os_mm_cartographic_symbol (writer SPATIALITE_1)
os_mm_cartographic_symbol (writer SPATIALITE_1)
    attributes: os_id string(20), feature_code integer, theme string(64), descriptive_group string(40), descriptive_term string(40), orientation integer, surface_level integer, change_history string(1024), last_change_date date, osmmstyle_name string(70), version integer, version_date date, mi_prinx integer, mi_style string(255)
Note: Remove input-dataset / attributes we don't want
AttributeRemover_15
    REMOVE_ATTRS = AccuracyOfHeightAboveGroundLevel,AnchorPosition,Font,Height,HeightAboveGroundLevel,NonBoundingLine,Orientation,PhysicalPresence,TextString,_feature_type
    -> AttributeRenamer_6
AttributeRenamer_6
    ATTR_LIST = CHANGE_HISTORY,Change_Hist_String,DESCRIPTIVE_GROUP,DescriptiveGroup,DESCRIPTIVE_TERM,DescriptiveTerm,FEATURE_CODE,FeatureCode,OS_ID,TOID,THEME,Theme,LAST_CHANGE_DATE,Last_Change_Date,SURFACE_LEVEL,PhysicalLevel,ACCURACY_OF_POSITION,AccuracyOfPosition,ACCURACY_OF_DATUM_HEIGHT,AccuracyOfHeightAboveDatum,HEIGHT_ABOVE_DATUM,HeightAboveDatum,MAKE,Make,VERSION,Version,VERSION_DATE,VersionDate
    -> CoordinateRounder_4
Note: [optimisation] (smaller file space). / We only need two digits of precision / (not even that really).
CoordinateRounder_4
    ZPREC = 0
    YPREC = 2
    XPREC = 2
    ROUNDED -> AttributeRemover_13
Note: Remove FME-generated attributes we don't want
AttributeRemover_13
    REMOVE_ATTRS = _x_orig,_y_orig,_x_anchor,_y_anchor,stylename,_geometry,_x_offset,_y_offset
    -> Counter_2
Counter_2
    SCOPE = Local
    START = 1
    DOMAIN = counter
    CNT_ATTR = MI_PRINX
    -> os_mm_topographic_point (writer SPATIALITE_1)
os_mm_topographic_point (writer SPATIALITE_1)
    attributes: os_id string(20), feature_code integer, theme string(64), accuracy_of_position string(4), descriptive_group string(40), descriptive_term string(40), make string(12), height_above_datum real(31,15), accuracy_of_datum_height string(4), surface_level integer, change_history string(1024), last_change_date date, osmmstyle_name string(70), version integer, version_date date, mi_prinx integer, mi_style string(255)
Note: No Point to Line Conversion
No Point to Line Conversion (writer CSV_1)
    attributes: _x_anchor char(20), DescriptiveTerm char(20), FeatureCode char(20), _y_anchor char(20), AnchorPosition char(20), PhysicalLevel char(20), _geometry char(20), AccuracyOfHeightAboveDatum char(20), _y_orig char(20), DescriptiveGroup char(20), Change_Hist_String char(20), feat_code char(20), _feature_type char(20), Orientation char(20), HeightAboveDatum char(20), AccuracyOfPosition char(20), AccuracyOfHeightAboveGroundLevel char(20), NonBoundingLine char(20), HeightAboveGroundLevel char(20), Font char(20), TextString char(20), PhysicalPresence char(20), MI_STYLE char(20), Make char(20), Version char(20), Last_Change_Date char(20), _x_orig char(20), Height char(20), TOID char(20), Theme char(20),
      VersionDate char(20), OSMMSTYLE_NAME char(20)

Bookmark: String re-organiser (DescriptiveGroup)
Note: Some input data has multiple DescriptiveGroup entries. / Unfortunately the OS hasn't seen fit to ensure they are / always in the same order, so we need to explode them and / then sort them so they always come through in the same order. / This allows efficient matching with the OSMM styles we have / on record.

Bookmark: String re-organiser (DescriptiveTerm)
Note: Some input data has multiple DescriptiveTerm entries. / Unfortunately the OS hasn't seen fit to ensure they are / always in the same order, so we need to explode them and / then sort them so they always come through in the same order. / This allows efficient matching with the OSMM styles we have / on record.

Bookmark: Change-History concatenator
Note: We concatenate the change history from a List into a single string here.

Bookmark: OSMMSTYLE_NAME joiner
Note: All of these string concatenators ensure / that the Joiner works properly. / Different OSMM layers use different attributes / for the OSMM Styling, so we need separate / concatenator

Bookmark: Get symbol anchor co-ordinates
Note: The line symbols are fairly randomly drawn, / with the starting/ending vertex possibly being anywhere. / Also they're scattered all over the Midlands.
Note: With these transformers we're calculating exactly where / the anchor for the symbol is based on what the text-string / "centroid" attribute tells us.
Note: These anchors are later used to ensure the symbol is placed in exactly / the right place. They're also used for rotation.

Bookmark: Point to Line Conversion
Note: Topographic Point and Cartopgraphic Symbol / both need to be converted from points to line symbols.
Note: Using the anchor points calculated / earlier, these transformers move the / geometry to the correct location.

Bookmark: Topographic Line
Note: OSMM.OS_MM_TOPOGRAPHIC_LINE

Bookmark: Topographic Area
Note: OSMM.OS_MM_TOPOGRAPHIC_AREA

Bookmark: Boundary Line
Note: OSMM.OS_MM_BOUNDARYLINE

Bookmark: Create all bounds for text box
Note: Turns the text into text, then get's the co-ordinates / for a bounding box that would surround it / That includes not only max/min but also a mid point

Bookmark: Reposition text in relation to anchor point
Note: The OS use an attribute called "anchorPosition" which tells us where the text should be in relation to the anchor point. / FME uses a fixed bottom-left anchor point, so we need to move our text in relation to that. / These Filters figure out where we're moving to.

Bookmark: Rotation
Note: Rotate the symbol around the anchor. / The OS provide the orientation in tenths / of a degree.

Bookmark: Topographic Point
Note: OSMM.OS_MM_TOPOGRAPHIC_POINT

Bookmark: Cartographic Symbol
Note: OSMM.OS_MM_CARTOGRAPHIC_SYMBOL

Bookmark: Create line
Note: The new line goes down the / vertical centre of the text / bounding box.

Bookmark: Offset
Note: Offset the line based on / where the AnchorPosition is.

Bookmark: Cartographic Text
Note: This bookmark takes the Cartographic Text inputs - text string and anchor point, then creates / a line that GISs will use as the basis for text placement. / The line is correctly placed and rotated in relation to the anchor point.
Note: OSMM.OS_MM_CARTOGRAPHIC_TEXT

FME custom transformer AttributeExistenceChecker
Checks whether the specified attribute exists.

Parameters:
- VAL = value   # Value

Note: 2010-06-24 - Hans van der Maarel, Red Geographics / Developed this custom transformer to check whether or not / an attribute exists. Many thanks to Oliver's Python Corner on / FMEPedia. / If you have any questions feel free to contact me at / hans@redgeographics.com or through the FMETalk group.
INPUT (input)
    -> AttributeCreator_3
Note: Star-Apic, 6/9/11 / I have made one small change here and it is to do / with publuished parameters again and the way / they are used. / In the previous version a 'Text' published parameter was created new. From / the Published Parameter list right-click and go Add Parameter. The parameter was / then linked through to the AttributeSetter argument. You can link a parameter by / going to the transformer argument, right-clicking and going 'link'. / My alternative method was to create the parameter directly from the transformer / argument itself. This interprets the input value and in this case would create an / attribute pick list. / Its just a small difference bewteen how the parameter is created and how it is applied.
AttributeCreator_3
    ATTR_LIST = lookfor,foo
    -> PythonCaller [off]
    -> AttributeSetter
AttributeSetter
    VAL = $(VAL)
    DEST_ATTR = lookfor
    -> PythonCaller
PythonCaller
    PYTHONSOURCE:
      import pyfme

      class MyPythonFactory(object):
          def __init__(self):
              self.count_features = 0
              self.logger = pyfme.FMELogfile()

          def input(self,feature):
              self.count_features += 1

              self.lookfor = feature.getAttribute('lookfor')

              # Accessing all attributes of a feature
              self.all_attributes = feature.getAllAttributeNames() # return a list with all attribute names as result
              self.all_attributes_count = len(self.all_attributes) # count attributes

              self.logger.log('Feature: '+ str(self.count_features),1)

              for i in range(self.all_attributes_count):
                  self.attribute_name  = self.all_attributes[i]                     # get attribute name
                  if self.attribute_name == self.lookfor:
                      self.found = 1
                      break
                  else:
                      self.found = 0

              feature.setAttribute('_found',self.found)

              self.logger.log('\n',1)
              self.pyoutput(feature)

          def close(self):
              self.logger.log('Total number of features: ' + str(self.count_features),1)
    PYTHONSYMBOL = MyPythonFactory
    -> AttributeExposer
AttributeExposer
    ATTR_LIST = _found
    -> AttributeRemover
AttributeRemover
    REMOVE_ATTRS = lookfor
    -> TestFilter
TestFilter
    TEST_LIST = TEST_CLAUSE,"TEST @Value(_found) = 1",TEST_LIST,"&_found,=,1",TEST_MODE,Automatic,BOOL_OP,OR,exists
    exists -> EXIST (output)
    <UNFILTERED> -> NOT_EXIST (output)
EXIST (output)
NOT_EXIST (output)

FME custom transformer AttributeNameFinder

Parameters:
- ATTR_NAME = input_words   # " " Enter all possible attribute names (, seperated)
- DEST_ATTR =   # Name of output attribute

Input (input)
    -> AttributeExposer
AttributeExposer
    ATTR_LIST = _iteration,_elements_in_list
    -> Tester
Tester
    TEST_MODE = Automatic
    BOOL_OP = OR
    TEST_LIST = &_iteration,>=,1
    TEST_CLAUSE = TEST @Value(_iteration) >= 1
    PASSED -> ListIndexer
    FAILED -> AttributeSplitter
AttributeSplitter
    LIST_NAME = _list_of_words
    ATTR_NAME = $(ATTR_NAME)
    DELIMITER = ,
    TRIM_OPTION = Both
    DROP_EMPTY_PARTS = No
    -> ListElementCounter
ListElementCounter
    LIST_NAME = _list_of_words{}
    CNT_ATTR = _elements_in_list
    -> ExpressionEvaluator_2
ExpressionEvaluator_2
    VAL_ATTR = _elements_in_list
    EXPRESSION = (@Value(_elements_in_list)-1)
    -> AttributeSetter
Note: Ok firstly an apology I cant help tidying up. / Go to Navigator > Parameters > Published Parameters and expand them. You will see two new published parameters. / The first parameter feeds into the transformer attribute splitter. / The second parameter feeds into the transformer AttributeSetter_Exists. / I have slightly changed the way you handle the result once the Exists test works. I have used an AttributeSetter rather / than an AttributeCopier. This is because it allow me to get a handle on teh output attribute more easily. / E.g. / I create one of the parameters by going to navigator > Transformers, expanded the transformer / AttributeSplitter, right-clicked 'Attribute To Split' and said create parameter. Important to remember this creates / an attribute pick list!
AttributeSetter
    VAL = 0
    DEST_ATTR = _iteration
    -> ListIndexer
ListIndexer
    LIST_ATTR = _list_of_words{}
    INDEX = @Value(_iteration)
    -> AttributeExistenceChecker
AttributeExistenceChecker
    VAL = @Value(_list_of_words)
    NOT_EXIST -> Tester_Index_limit
    EXIST -> AttributeSetter_Exists
AttributeSetter_Exists
    VAL = @Value(_list_of_words)
    DEST_ATTR = $(DEST_ATTR)
    -> AttributeRemover_2
AttributeRemover_2
    REMOVE_ATTRS = _elements_in_list,_found,_iteration,_list_of_words
    -> ListRemover
ListRemover
    LIST_ATTRS = _list_of_words{}
    -> Exists (output)
Exists (output)
Tester_Index_limit
    TEST_MODE = Automatic
    BOOL_OP = OR
    TEST_LIST = &_iteration,=,&_elements_in_list
    TEST_CLAUSE = TEST @Value(_iteration) = @Value(_elements_in_list)
    FAILED -> ExpressionEvaluator
    PASSED -> AttributeRemover
AttributeRemover
    REMOVE_ATTRS = _elements_in_list,_found,_iteration,_list_of_words
    -> ListRemover_2
ListRemover_2
    LIST_ATTRS = _list_of_words{}
    -> Doesn't_Exist (output)
Doesn't_Exist (output)
ExpressionEvaluator
    VAL_ATTR = _iteration
    EXPRESSION = (@Value(_iteration)+1)
    -> Input (output)
Input (output)

FME custom transformer ListAttributeAccumulator
Accumulates values from a list into a single attribute passed as an argument.
Values are separated by a comma. This could be changed by usage of a published parameter or a constant! 
This is not generic but created as an example because the list to be exposed may contain different values attributes which can only be accounted for by manually hard coding them.
At the moment to only values that will accumulated are:
1. ReasonForChange
2. ChangeDate
Example list:
ChangeHistory{0}.ChangeDate = 20010128
ChangeHistory{0}.ReasonForChange = New
ChangeHistory{1}.ReasonForChange = Attributes
ChangeHistory{1}.ChangeDate = 20031103
The value of the new attributes would become:
New,20010128 ,Attributes,20031103
New list values can be added by exposing in the AttributeExposer and adding in the two StringConcatenator transformers.

Parameters:
- LIST_NAME = ChangeHistory{}   # LIST_NAME " " List Attribute

INPUT (input)
    -> AttributeExposer_2
Note: expose attr to be used / with transformer
AttributeExposer_2
    ATTR_LIST = _AccumulatedListValues,_iteration_count,ChangeDate,ReasonForChange
    -> Tester
Note: Test the current index / position attr, if this is / the first loop it will not / have existed before / so will have no value.
Tester
    TEST_MODE = Automatic
    BOOL_OP = OR
    TEST_LIST = &_iteration_count,>=,1
    TEST_CLAUSE = TEST @Value(_iteration_count) >= 1
    PASSED -> ListIndexer
    FAILED -> ListElementCounter_2
ListElementCounter_2
    LIST_NAME = $(LIST_NAME)
    CNT_ATTR = _element_count
    -> ExpressionEvaluator_element_index
ExpressionEvaluator_element_index
    VAL_ATTR = _element_count
    EXPRESSION = (@Value(_element_count)-1)
    -> AttributeSetter
AttributeSetter
    VAL = 0
    DEST_ATTR = _iteration_count
    -> ListIndexer
Note: Demote the list values for / the current list index to attr
ListIndexer
    LIST_ATTR = $(LIST_NAME)
    INDEX = @Value(_iteration_count)
    -> Tester_3
Tester_3
    TEST_MODE = Automatic
    BOOL_OP = OR
    TEST_LIST = &_AccumulatedListValues,=,""
    TEST_CLAUSE = TEST @Value(_AccumulatedListValues) = ""
    FAILED -> StringConcatenator_2
    PASSED -> StringConcatenator
StringConcatenator
    PARM_LINE = &ChangeDate,,,&ReasonForChange
    VAL_ATTR = _AccumulatedListValues
    -> Tester_Indecies
Note: Adrian Porter / STAR-APIC UK / 3/8/2011 / Accumulates values from a list into a single attribute passed as an argument. / Values are separated by a comma. This could be changed by usage of a published parameter or a constant! / This is not generic but created as an example because the list to be exposed may contain different values / attributes which can only be accounted for by manually hard coding them. / At the moment to only values that will accumulated are: / 1. ReasonForChange / 2. ChangeDate / Example list: / ChangeHistory{0}.ChangeDate = 20010128 / ChangeHistory{0}.ReasonForChange = New / ChangeHistory{1}.ReasonForChange = Attributes / ChangeHistory{1}.ChangeDate = 20031103 / The value of the new attributes would become: / New,20010128 ,Attributes,20031103 / New list values can be added by exposing in the AttributeExposer and adding in the two StringConcatenator transformers.
StringConcatenator_2
    PARM_LINE = &_AccumulatedListValues,;,&ChangeDate,,,&ReasonForChange
    VAL_ATTR = _AccumulatedListValues
    -> Tester_Indecies
Note: have we reached the / last index of the list
Tester_Indecies
    TEST_MODE = Automatic
    BOOL_OP = OR
    TEST_LIST = &_iteration_count,=,&_element_count
    TEST_CLAUSE = TEST @Value(_iteration_count) = @Value(_element_count)
    FAILED -> ExpressionEvaluator_2
    PASSED -> AttributeSetter_2
Note: The final output copy the / internal result attr value to / the user defined attr
AttributeSetter_2
    VAL = @Value(_AccumulatedListValues)
    DEST_ATTR = Change_Hist_String
    -> AttributeSetter_3
Note: Sets the date of last change attribute
AttributeSetter_3
    VAL = @Value(ChangeDate)
    DEST_ATTR = Last_Change_Date
    -> AttributeRemover
Note: clean up attr created / within transformer
AttributeRemover
    REMOVE_ATTRS = _AccumulatedListValues,_element_count,_iteration_count
    -> OUTPUT (output)
OUTPUT (output)
Note: Increase index position / for next loop
ExpressionEvaluator_2
    VAL_ATTR = _iteration_count
    EXPRESSION = (@Value(_iteration_count)+1)
    -> INPUT (output)
INPUT (output)

Bookmark: Set indecies
Note: Set index maxiumum: size / of the list decremented by / one because list start / at zero. / Set starting index position / to be zero

Bookmark: Result builder
Note: build up result attr from / exposed list attr values
