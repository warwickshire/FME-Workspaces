FME workspace VMD Loader from Shapefile - UPDATE- v2.fmw

Parameters:
- DestDataset_ORACLE8I = co_gislive   # Destination Oracle Spatial Object Service
- SourceDataset_SHAPE_3 = Q:\GIS_DATA\ZZ Original GIS Data\01 Ordnance Survey\VectorMap District\2014-04-22\*.zip\**\*.shp   # Source Esri Shape File(s)
- FEATURE_TYPES =

Readers:
- SHAPE_1: SHAPE from $(SourceDataset_SHAPE_3) in BritishNatGrid

Writers:
- ORACLE8I_1: ORACLE8I to $(DestDataset_ORACLE8I) in BritishNatGrid

SJ_AdministrativeBoundary (reader SHAPE_1)
    attributes: CLASSIFICA char(254), FEATCODE number(5,0), JUNCTIONNU char(254), FONTTYPE number(4,0), ORIENTATIO number(4,0), HTMLNAME char(254), DFTNUMBER char(254), FONTCOLOUR number(4,0), HEIGHT number(5,0), FONTHEIGHT number(4,0), NAME char(254)
    -> SubstringExtractor
Note: VML Tiles all come with the TileCode prefixed / This dumps the tile-code so we can group by tile / when outputting
SubstringExtractor
    RESULT_ATTR = _substring
    SRC_ATTR = fme_basename
    START = 3
    END = -1
    -> GeometryValidator
GeometryValidator
    CHECK_HOLE_TOUCHING_POLYGON = No
    DUP_COORDS_CHECK_Z = No
    NULL_REMOVAL = NULL_REMOVAL
    TYPE_REPAIR = TYPE_REPAIR
    SELF_INTERSECTING = SELF_INTERSECTING
    PRESETS = Basic Geometry Integrity
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = Yes
    PLANAR_TOLERANCE_MODE = Auto
    NAN_REMOVAL = NAN_REMOVAL
    CONSECUTIVE_IDENTICAL_VERTICES_2D = CONSECUTIVE_IDENTICAL_VERTICES_2D
    PASSED -> GeometryFilter
    REPAIRED -> GeometryFilter
GeometryFilter
    BREAK_AGG = No
    AREA -> SpikeRemover
    POINT -> GeometryValidator_2
    LINE -> GeometryValidator_2
    ARC -> GeometryValidator_2
    ELLIPSE -> GeometryValidator_2
    TEXT -> GeometryValidator_2
Note: Remove spikes from buildings
SpikeRemover
    SPIKEANGLE = 5
    UNCHANGED -> GeometryValidator_2
    CHANGED -> GeometryValidator_2
Note: Last-ditch attempt to fix stuff
GeometryValidator_2
    SHELL_VALIDATION = SHELL_VALIDATION
    CHECK_HOLE_TOUCHING_POLYGON = No
    DUP_COORDS_CHECK_Z = No
    NULL_REMOVAL = NULL_REMOVAL
    TYPE_REPAIR = TYPE_REPAIR
    SELF_INTERSECTING = SELF_INTERSECTING
    PRESETS = All
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = Yes
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> GeometryValidator_3
    REPAIRED -> GeometryValidator_3
Note: Dump everything that still fails. / We're very paranoid.
GeometryValidator_3
    SHELL_VALIDATION = SHELL_VALIDATION
    CHECK_HOLE_TOUCHING_POLYGON = No
    DUP_COORDS_CHECK_Z = No
    NULL_REMOVAL = NULL_REMOVAL
    TYPE_REPAIR = TYPE_REPAIR
    SELF_INTERSECTING = SELF_INTERSECTING
    PRESETS = All
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PLANAR_SURFACE = PLANAR_SURFACE
    REPAIR = No
    MISSING_TEXTURE_COORDINATES = MISSING_TEXTURE_COORDINATES
    SOLID_VOID_REPAIR = SOLID_VOID_REPAIR
    OGC_SIMPLE_CHECK = OGC_SIMPLE_CHECK
    PLANAR_TOLERANCE_MODE = Auto
    NAN_REMOVAL = NAN_REMOVAL
    MISSING_VERTEX_NORMALS = MISSING_VERTEX_NORMALS
    OGC_VALID_CHECK = OGC_VALID_CHECK
    CONSECUTIVE_IDENTICAL_VERTICES_2D = CONSECUTIVE_IDENTICAL_VERTICES_2D
    PASSED -> TestFilter
TestFilter
    TEST_LIST = BOOL_OP,OR,COMPOSITE_TEST,<Unused>,TEST_CLAUSE,"TEST @Value(_substring) = AdministrativeBoundary",AdministrativeBoundary,BOOL_OP,OR,COMPOSITE_TEST,<Unused>,TEST_CLAUSE,"TEST @Value(_substring) = Airport",Airport,BOOL_OP,OR,COMPOSITE_TEST,<Unused>,TEST_CLAUSE,"TEST @Value(_substring) = Building",Building,BOOL_OP,OR,COMPOSITE_TEST,<Unused>,TEST_CLAUSE,"TEST @Value(_substring) = ElectricityTransmissionLine",ElectricityTransmissionLine,BOOL_OP,OR,COMPOSITE_TEST,<Unused>,TEST_CLAUSE,"TEST @Value(_substring) = Foreshore",Foreshore,BOOL_OP,OR,COMPOSITE_TEST,<Unused>,TEST_CLAUSE,"TEST @Value(_substring) = Glasshouse",Glasshouse,BOOL_OP,OR,COMPOSITE_TEST,<Unused>,TEST_CLAUSE,"TEST @Value(_substring) = HeritageSite",HeritageSite,BOOL_OP,OR,COMPOSITE_TEST,<Unused>,TEST_CLAUSE,"TEST @Value(_substring) = Land",Land,BOOL_OP,OR,COMPOSITE_TEST,<Unused>,TEST_CLAUSE,"TEST @Value(_substring) = MotorwayJunction",MotorwayJunction,BOOL_OP,OR,COMPOSITE_TEST,<Unused>,TEST_CLAUSE,"TEST @Value(_substring) = NamedPlace",NamedPlace,BOOL_OP,OR,COMPOSITE_TEST,<Unused>,TEST_CLAUSE,"TEST @Value(_substring) = Ornament",Ornament,BOOL_OP,OR,COMPOSITE_TEST,<Unused>,TEST_CLAUSE,"TEST @Value(_substring) = PublicAmenity",PublicAmenity,BOOL_OP,OR,COMPOSITE_TEST,<Unused>,TEST_CLAUSE,"TEST @Value(_substring) = RailwayStation",RailwayStation,BOOL_OP,OR,COMPOSITE_TEST,<Unused>,TEST_CLAUSE,"TEST @Value(_substring) = RailwayTrack",RailwayTrack,BOOL_OP,OR,COMPOSITE_TEST,<Unused>,TEST_CLAUSE,"TEST @Value(_substring) = RailwayTunnel",RailwayTunnel,BOOL_OP,OR,COMPOSITE_TEST,<Unused>,TEST_CLAUSE,"TEST @Value(_substring) = Road",Road,BOOL_OP,OR,COMPOSITE_TEST,<Unused>,TEST_CLAUSE,"TEST @Value(_substring) = RoadTunnel",RoadTunnel,BOOL_OP,OR,COMPOSITE_TEST,<Unused>,TEST_CLAUSE,"TEST @Value(_substring) = Roundabout",Roundabout,BOOL_OP,OR,COMPOSITE_TEST,<Unused>,TEST_CLAUSE,"TEST @Value(_substring) = SpotHeight",SpotHeight,BOOL_OP,OR,COMPOSITE_TEST,<Unused>,TEST_CLAUSE,"TEST @Value(_substring) = SurfaceWater_Area",SurfaceWater_Area,BOOL_OP,OR,COMPOSITE_TEST,<Unused>,TEST_CLAUSE,"TEST @Value(_substring) = SurfaceWater_Line",SurfaceWater_Line,BOOL_OP,OR,COMPOSITE_TEST,<Unused>,TEST_CLAUSE,"TEST @Value(_substring) = TidalBoundary",TidalBoundary,BOOL_OP,OR,COMPOSITE_TEST,<Unused>,TEST_CLAUSE,"TEST @Value(_substring) = TidalWater",TidalWater,BOOL_OP,OR,COMPOSITE_TEST,<Unused>,TEST_CLAUSE,"TEST @Value(_substring) = Woodland",Woodland
    DEFAULT_VALUE = <UNFILTERED>
    Airport -> Counter_3
    Foreshore -> Counter_21
    Glasshouse -> Counter_8
    HeritageSite -> Counter_23
    Land -> Dissolver
    MotorwayJunction -> Counter_9
    NamedPlace -> Counter_17
    Ornament -> Counter_20
    PublicAmenity -> Counter_16
    RailwayStation -> Counter_12
    RailwayTunnel -> Counter_4
    RoadTunnel -> Counter_10
    Roundabout -> Counter_24
    SpotHeight -> Counter
    SurfaceWater_Area -> Counter_2
    TidalBoundary -> Counter_22
    TidalWater -> Counter_11
    Woodland -> Counter_19
    Road -> LineJoiner
    RailwayTrack -> LineJoiner_2
    ElectricityTransmissionLine -> LineJoiner_3
    SurfaceWater_Line -> LineJoiner_4
    Building -> GeometryFilter_2
    AdministrativeBoundary -> GeometryFilter_3
GeometryFilter_3
    BREAK_AGG = No
    LINE -> Counter_14
Note: Clips to Approx the bounding box of a 20km buffer around Warwickshire
Counter_14
    SCOPE = Local
    START = 1
    DOMAIN = counter
    CNT_ATTR = MI_PRINX
    -> OSMM.OS_VMD_ADMIN_BOUNDARY (writer ORACLE8I_1)
OSMM.OS_VMD_ADMIN_BOUNDARY (writer ORACLE8I_1)
    attributes: FEATCODE number(5,0), CLASSIFICATION varchar2(254), MI_PRINX integer, MI_STYLE varchar2(255)
Counter_3
    SCOPE = Local
    START = 1
    DOMAIN = counter
    CNT_ATTR = MI_PRINX
    -> OSMM.OS_VMD_AIRPORT (writer ORACLE8I_1)
OSMM.OS_VMD_AIRPORT (writer ORACLE8I_1)
    attributes: FEATCODE number(5,0), NAME varchar2(254), MI_PRINX integer, MI_STYLE varchar2(255)
GeometryFilter_2
    BREAK_AGG = No
    AREA -> Counter_18
Counter_18
    SCOPE = Local
    START = 1
    DOMAIN = counter
    CNT_ATTR = MI_PRINX
    -> OSMM.OS_VMD_BUILDING (writer ORACLE8I_1)
OSMM.OS_VMD_BUILDING (writer ORACLE8I_1)
    attributes: FEATCODE number(5,0), MI_PRINX integer, MI_STYLE varchar2(255)
LineJoiner_3
    GROUP_BY = FEATCODE
    GROUP_BREAK = no
    PRESERVE = no
    TOPOLOGY = End noded
    LINES_AS_SEGMENTS = No
    CONSIDER_NODE_ELEVATION = no
    BREAK = no
    LINE -> Counter_7
Counter_7
    SCOPE = Local
    START = 1
    DOMAIN = counter
    CNT_ATTR = MI_PRINX
    -> OSMM.OS_VMD_ELEC_TRANSMISSION_LINE (writer ORACLE8I_1)
OSMM.OS_VMD_ELEC_TRANSMISSION_LINE (writer ORACLE8I_1)
    attributes: FEATCODE number(5,0), MI_PRINX integer, MI_STYLE varchar2(255)
Counter_21
    SCOPE = Local
    START = 1
    DOMAIN = counter
    CNT_ATTR = MI_PRINX
    -> OSMM.OS_VMD_FORESHORE (writer ORACLE8I_1)
OSMM.OS_VMD_FORESHORE (writer ORACLE8I_1) [off]
    attributes: FEATCODE number(5,0), MI_PRINX integer, MI_STYLE varchar2(255)
Counter_8
    SCOPE = Local
    START = 1
    DOMAIN = counter
    CNT_ATTR = MI_PRINX
    -> OSMM.OS_VMD_GLASSHOUSE (writer ORACLE8I_1)
OSMM.OS_VMD_GLASSHOUSE (writer ORACLE8I_1)
    attributes: FEATCODE number(5,0), MI_PRINX integer, MI_STYLE varchar2(255)
Counter_23
    SCOPE = Local
    START = 1
    DOMAIN = counter
    CNT_ATTR = MI_PRINX
    -> OSMM.OS_VMD_HERITAGE_SITE (writer ORACLE8I_1)
OSMM.OS_VMD_HERITAGE_SITE (writer ORACLE8I_1)
    attributes: FEATCODE number(5,0), NAME varchar2(254), MI_PRINX integer, MI_STYLE varchar2(255)
Note: "Land" is a grid. Bah
Dissolver
    GROUP_BY = FEATCODE
    NO_OVRLP = No
    ACCUM_INPUT_ATTRS = No
    AREA -> Counter_15
Counter_15
    SCOPE = Local
    START = 1
    DOMAIN = counter
    CNT_ATTR = MI_PRINX
    -> OSMM.OS_VMD_LAND (writer ORACLE8I_1)
OSMM.OS_VMD_LAND (writer ORACLE8I_1)
    attributes: FEATCODE number(5,0), MI_PRINX integer, MI_STYLE varchar2(255)
Counter_9
    SCOPE = Local
    START = 1
    DOMAIN = counter
    CNT_ATTR = MI_PRINX
    -> OSMM.OS_VMD_MOTORWAY_JUNCTIONS (writer ORACLE8I_1)
OSMM.OS_VMD_MOTORWAY_JUNCTIONS (writer ORACLE8I_1)
    attributes: FEATCODE number(5,0), JUNCTION_NUMBER varchar2(254), MI_PRINX integer, MI_STYLE varchar2(255)
Counter_17
    SCOPE = Local
    START = 1
    DOMAIN = counter
    CNT_ATTR = MI_PRINX
    -> OSMM.OS_VMD_NAMED_PLACE (writer ORACLE8I_1)
Note: HTMLNAME is the same as name, but made HTML safe (so &amp; etc)
OSMM.OS_VMD_NAMED_PLACE (writer ORACLE8I_1)
    attributes: FEATCODE number(5,0), NAME varchar2(254), ORIENTATIO number(4,0), FONTCOLOUR number(4,0), FONTHEIGHT number(4,0), FONTTYPE number(4,0), MI_PRINX integer, MI_STYLE varchar2(255)
Counter_20
    SCOPE = Local
    START = 1
    DOMAIN = counter
    CNT_ATTR = MI_PRINX
    -> OSMM.OS_VMD_ORNAMENT (writer ORACLE8I_1)
OSMM.OS_VMD_ORNAMENT (writer ORACLE8I_1)
    attributes: FEATCODE number(5,0), MI_PRINX integer, MI_STYLE varchar2(255)
Counter_16
    SCOPE = Local
    START = 1
    DOMAIN = counter
    CNT_ATTR = MI_PRINX
    -> OSMM.OS_VMD_PUBLIC_AMENITY (writer ORACLE8I_1)
OSMM.OS_VMD_PUBLIC_AMENITY (writer ORACLE8I_1)
    attributes: FEATCODE number(5,0), CLASSIFICATION varchar2(254), MI_PRINX integer, MI_STYLE varchar2(255)
Counter_12
    SCOPE = Local
    START = 1
    DOMAIN = counter
    CNT_ATTR = MI_PRINX
    -> OSMM.OS_VMD_RAILWAY_STATION (writer ORACLE8I_1)
OSMM.OS_VMD_RAILWAY_STATION (writer ORACLE8I_1)
    attributes: FEATCODE number(5,0), NAME varchar2(254), CLASSIFICATION varchar2(254), MI_PRINX integer, MI_STYLE varchar2(255)
LineJoiner_2
    GROUP_BY = CLASSIFICA FEATCODE
    GROUP_BREAK = no
    PRESERVE = no
    TOPOLOGY = End noded
    LINES_AS_SEGMENTS = No
    CONSIDER_NODE_ELEVATION = no
    BREAK = no
    LINE -> Counter_13
Counter_13
    SCOPE = Local
    START = 1
    DOMAIN = counter
    CNT_ATTR = MI_PRINX
    -> OSMM.OS_VMD_RAILWAY_TRACK (writer ORACLE8I_1)
OSMM.OS_VMD_RAILWAY_TRACK (writer ORACLE8I_1)
    attributes: FEATCODE number(5,0), CLASSIFICATION varchar2(254), MI_PRINX integer, MI_STYLE varchar2(255)
Counter_4
    SCOPE = Local
    START = 1
    DOMAIN = counter
    CNT_ATTR = MI_PRINX
    -> OSMM.OS_VMD_RAILWAY_TUNNEL (writer ORACLE8I_1)
OSMM.OS_VMD_RAILWAY_TUNNEL (writer ORACLE8I_1)
    attributes: FEATCODE number(5,0), MI_PRINX integer, MI_STYLE varchar2(255)
LineJoiner
    GROUP_BY = CLASSIFICA FEATCODE DFTNUMBER NAME
    GROUP_BREAK = no
    PRESERVE = no
    TOPOLOGY = End noded
    LINES_AS_SEGMENTS = No
    CONSIDER_NODE_ELEVATION = no
    BREAK = no
    LINE -> Counter_6
Counter_6
    SCOPE = Local
    START = 1
    DOMAIN = counter
    CNT_ATTR = MI_PRINX
    -> OSMM.OS_VMD_ROAD (writer ORACLE8I_1)
OSMM.OS_VMD_ROAD (writer ORACLE8I_1)
    attributes: FEATCODE number(5,0), NAME varchar2(254), DFTNUMBER varchar2(254), CLASSIFICATION varchar2(254), MI_PRINX integer, MI_STYLE varchar2(255)
Counter_10
    SCOPE = Local
    START = 1
    DOMAIN = counter
    CNT_ATTR = MI_PRINX
    -> OSMM.OS_VMD_ROAD_TUNNEL (writer ORACLE8I_1)
OSMM.OS_VMD_ROAD_TUNNEL (writer ORACLE8I_1)
    attributes: FEATCODE number(5,0), MI_PRINX integer, MI_STYLE varchar2(255)
Counter_24
    SCOPE = Local
    START = 1
    DOMAIN = counter
    CNT_ATTR = MI_PRINX
    -> OSMM.OS_VMD_ROUNDABOUT (writer ORACLE8I_1)
OSMM.OS_VMD_ROUNDABOUT (writer ORACLE8I_1)
    attributes: FEATCODE number(5,0), CLASSIFICATION varchar2(254), MI_PRINX integer, MI_STYLE varchar2(255)
Counter
    SCOPE = Local
    START = 1
    DOMAIN = counter
    CNT_ATTR = MI_PRINX
    -> OSMM.OS_VMD_SPOTHEIGHT (writer ORACLE8I_1)
OSMM.OS_VMD_SPOTHEIGHT (writer ORACLE8I_1)
    attributes: FEATCODE number(5,0), HEIGHT number(5,0), MI_PRINX integer, MI_STYLE varchar2(255)
Counter_2
    SCOPE = Local
    START = 1
    DOMAIN = counter
    CNT_ATTR = MI_PRINX
    -> OSMM.OS_VMD_SURFACE_WATER_AREA (writer ORACLE8I_1)
OSMM.OS_VMD_SURFACE_WATER_AREA (writer ORACLE8I_1)
    attributes: FEATCODE number(5,0), MI_PRINX integer, MI_STYLE varchar2(255)
LineJoiner_4
    GROUP_BY = FEATCODE
    GROUP_BREAK = no
    PRESERVE = no
    TOPOLOGY = End noded
    LINES_AS_SEGMENTS = No
    CONSIDER_NODE_ELEVATION = no
    BREAK = no
    LINE -> Counter_5
Counter_5
    SCOPE = Local
    START = 1
    DOMAIN = counter
    CNT_ATTR = MI_PRINX
    -> OSMM.OS_VMD_SURFACE_WATER_LINE (writer ORACLE8I_1)
OSMM.OS_VMD_SURFACE_WATER_LINE (writer ORACLE8I_1)
    attributes: FEATCODE number(5,0), MI_PRINX integer, MI_STYLE varchar2(255)
Counter_22
    SCOPE = Local
    START = 1
    DOMAIN = counter
    CNT_ATTR = MI_PRINX
    -> OSMM.OS_VMD_TIDAL_BOUNDARY (writer ORACLE8I_1)
OSMM.OS_VMD_TIDAL_BOUNDARY (writer ORACLE8I_1) [off]
    attributes: FEATCODE number(5,0), CLASSIFICATION varchar2(254), MI_PRINX integer, MI_STYLE varchar2(255)
Counter_11
    SCOPE = Local
    START = 1
    DOMAIN = counter
    CNT_ATTR = MI_PRINX
    -> OSMM.OS_VMD_TIDAL_WATER (writer ORACLE8I_1)
OSMM.OS_VMD_TIDAL_WATER (writer ORACLE8I_1) [off]
    attributes: FEATCODE number(5,0), MI_PRINX integer, MI_STYLE varchar2(255)
Counter_19
    SCOPE = Local
    START = 1
    DOMAIN = counter
    CNT_ATTR = MI_PRINX
    -> OSMM.OS_VMD_WOODLAND (writer ORACLE8I_1)
OSMM.OS_VMD_WOODLAND (writer ORACLE8I_1)
    attributes: FEATCODE number(5,0), MI_PRINX integer, MI_STYLE varchar2(255)
